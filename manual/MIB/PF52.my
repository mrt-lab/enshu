--
-- Copyright(C) 2010-2011 NEC Corporation. All Rights Reserved
--
-- PF5200-MIB.my: ProgrammableFlow Switching System information MIB file
--
PF5200 DEFINITIONS ::= BEGIN
IMPORTS
enterprises, OBJECT-TYPE, IpAddress,
Counter, Gauge, TimeTicks
    FROM RFC1155-SMI
RouterID, AreaID, Status, BigMetric, DesignatedRouterPriority,
HelloRange, Metric, PositiveInteger, UpToMaxAge
    FROM OSPF-MIB
OBJECT-TYPE
    FROM RFC-1212
TRAP-TYPE
    FROM RFC-1215
ifIndex
    FROM IF-MIB
DisplayString
    FROM RFC1213-MIB
RowStatus, MacAddress, TruthValue, TimeStamp
    FROM SNMPv2-TC
InterfaceIndex
    FROM IF-MIB
Ipv6IfIndex, Ipv6Address, Ipv6AddressPrefix
    FROM IPV6-TC
BridgeId, Timeout
    FROM BRIDGE-MIB
PortList
    FROM Q-BRIDGE-MIB
InetAddressType,InetAddress
    FROM INET-ADDRESS-MIB
;


VlanIndex ::= INTEGER (1..2147483647)
VlanIdOrZero ::= INTEGER (0|1..4094)
--BITS ::= OCTET STRING

-- object syntax difinition end

nec                             OBJECT IDENTIFIER ::= { enterprises 119 }
necProduct                      OBJECT IDENTIFIER ::= { nec 1 }
pf                              OBJECT IDENTIFIER ::= { necProduct 203 }
pf5000                          OBJECT IDENTIFIER ::= { pf 2 }
pf5200                          OBJECT IDENTIFIER ::= { pf5000 2 }
pf5200TrapId                    OBJECT IDENTIFIER ::= { pf5200 1 }
pf5240f-48t4xw                  OBJECT IDENTIFIER ::= { pf5200 41 }
pf5240r-48t4xw                  OBJECT IDENTIFIER ::= { pf5200 42 }

nec-mib                         OBJECT IDENTIFIER ::= { nec 2 }
necProductDepend                OBJECT IDENTIFIER ::= { nec-mib 3 }
pf-mib                          OBJECT IDENTIFIER ::= { necProductDepend 203 }
pf5000-mib                      OBJECT IDENTIFIER ::= { pf-mib 2 }
pf5000Common-mib                OBJECT IDENTIFIER ::= { pf5000-mib 10 }
pf5200-mib                      OBJECT IDENTIFIER ::= { pf5000-mib 2 }

-- device independent
pf5000Stats                     OBJECT IDENTIFIER ::= { pf5000Common-mib 1 }
pf5000PhysStats                 OBJECT IDENTIFIER ::= { pf5000Stats 1 }
pf5000IfStats                   OBJECT IDENTIFIER ::= { pf5000Stats 4 }
pf5000QoS                       OBJECT IDENTIFIER ::= { pf5000Stats 6 }
pf5000EtherTxQoS                OBJECT IDENTIFIER ::= { pf5000QoS 1 }
pf5000DHCP                      OBJECT IDENTIFIER ::= { pf5000Stats 10 }

pf5000Gsrp                      OBJECT IDENTIFIER ::= { pf5000Common-mib 4 }
pf5000Fdb                       OBJECT IDENTIFIER ::= { pf5000Common-mib 5 }
pf5000Vlan                      OBJECT IDENTIFIER ::= { pf5000Common-mib 6 }
pf5000VlanBridge                OBJECT IDENTIFIER ::= { pf5000Vlan 1 }
pf5000VlanBridgeBase            OBJECT IDENTIFIER ::= { pf5000VlanBridge 1 }
pf5000VlanBridgeStp             OBJECT IDENTIFIER ::= { pf5000VlanBridge 2 }
pf5000VlanBridgeTp              OBJECT IDENTIFIER ::= { pf5000VlanBridge 4 }
pf5000VlanBridgeStatic          OBJECT IDENTIFIER ::= { pf5000VlanBridge 5 }
pf5000VlanTagTranslation        OBJECT IDENTIFIER ::= { pf5000Vlan 10 }

pf5000Oadp                      OBJECT IDENTIFIER ::= { pf5000Common-mib 7 }
pf5000OadpMIBObjects            OBJECT IDENTIFIER ::= { pf5000Oadp 1 }
pf5000OadpGlobalInfo            OBJECT IDENTIFIER ::= { pf5000OadpMIBObjects 1 }
pf5000OadpPortInfo              OBJECT IDENTIFIER ::= { pf5000OadpMIBObjects 2 }
pf5000OadpNeighborInfo          OBJECT IDENTIFIER ::= { pf5000OadpMIBObjects 3 }
pf5000OadpMIBNotifications      OBJECT IDENTIFIER ::= { pf5000Oadp 2 }

pf5000Flow                      OBJECT IDENTIFIER ::= { pf5000Common-mib 8 }
pf5000AccessFilterStats         OBJECT IDENTIFIER ::= { pf5000Flow 9 }
pf5000QosFlowStats              OBJECT IDENTIFIER ::= { pf5000Flow 11 }

pf5000L2ld                      OBJECT IDENTIFIER ::= { pf5000Common-mib 10 }
pf5000L2ldGlobalInfo            OBJECT IDENTIFIER ::= { pf5000L2ld 1 }

pf5000Ospf                      OBJECT IDENTIFIER ::= { pf5000Common-mib 14 }
pf5000OspfTrap                  OBJECT IDENTIFIER ::= { pf5000Ospf 16 }
pf5000OspfTraps                 OBJECT IDENTIFIER ::= { pf5000OspfTrap 2 }
pf5000Ospfv3                    OBJECT IDENTIFIER ::= { pf5000Common-mib 15 }

pf5000BootManagement            OBJECT IDENTIFIER ::= { pf5000Common-mib 51 }
pf5000Login                     OBJECT IDENTIFIER ::= { pf5000Common-mib 52 }

pf5000lldp                      OBJECT IDENTIFIER ::= { pf5000Common-mib 100 }
pf5000lldpConfiguration         OBJECT IDENTIFIER ::= { pf5000lldp 1 }
pf5000lldpStats                 OBJECT IDENTIFIER ::= { pf5000lldp 2 }
pf5000lldpLocalSystemData       OBJECT IDENTIFIER ::= { pf5000lldp 3 }
pf5000lldpRemoteSystemData      OBJECT IDENTIFIER ::= { pf5000lldp 4 }
pf5000lldpRemoteOriginInfoData  OBJECT IDENTIFIER ::= { pf5000lldp 20 }

pf5000Axrp                      OBJECT IDENTIFIER ::= { pf5000Common-mib 200 }

pf5200Switch                 OBJECT IDENTIFIER ::= { pf5200-mib 1 }
pf5200Software               OBJECT IDENTIFIER ::= { pf5200Switch 2 }
pf5200SystemMsg              OBJECT IDENTIFIER ::= { pf5200Switch 3 }
pf5200SnmpAgent              OBJECT IDENTIFIER ::= { pf5200Switch 4 }
pf5200License                OBJECT IDENTIFIER ::= { pf5200Switch 6 }
pf5200Device                 OBJECT IDENTIFIER ::= { pf5200-mib 2 }
pf5200Chassis                OBJECT IDENTIFIER ::= { pf5200Device 1 }
pf5200PhysLine               OBJECT IDENTIFIER ::= { pf5200Device 2 }
pf5200Management             OBJECT IDENTIFIER ::= { pf5200-mib 3 }
pf5200OperationCommand       OBJECT IDENTIFIER ::= { pf5200Management 1 }
pf5200FdbClearMIB            OBJECT IDENTIFIER ::= { pf5200OperationCommand 1 }
pf5200SystemManagementMIB    OBJECT IDENTIFIER ::= { pf5200OperationCommand 2 }


pf5000IfStatsTable OBJECT-TYPE
    SYNTAX  SEQUENCE OF Pf5000IfStatsTableEntry
    ACCESS  not-accessible
    STATUS  mandatory
    DESCRIPTION
        "A table containing extension statistics for more than 100,000,000
        bps interface."
    ::= { pf5000IfStats 1 }

pf5000IfStatsEntry OBJECT-TYPE
    SYNTAX  Pf5000IfStatsTableEntry
    ACCESS  not-accessible
    STATUS  mandatory
    DESCRIPTION
        "An entry containing extension statistics for interface."
    INDEX   { pf5000IfStatsIndex }
    ::= { pf5000IfStatsTable 1 }

    Pf5000IfStatsTableEntry ::=
        SEQUENCE {
            pf5000IfStatsIndex
                INTEGER,
            pf5000IfStatsName
                DisplayString,
            pf5000IfStatsInMegaOctets
                Counter,
            pf5000IfStatsInUcastMegaPkts
                Counter,
            pf5000IfStatsInMulticastMegaPkts
                Counter,
            pf5000IfStatsInBroadcastMegaPkts
                Counter,
            pf5000IfStatsOutMegaOctets
                Counter,
            pf5000IfStatsOutUcastMegaPkts
                Counter,
            pf5000IfStatsOutMulticastMegaPkts
                Counter,
            pf5000IfStatsOutBroadcastMegaPkts
                Counter,
            pf5000IfStatsHighSpeed
                Counter
        }

pf5000IfStatsIndex OBJECT-TYPE
    SYNTAX  INTEGER
    ACCESS  not-accessible
    STATUS  mandatory
    DESCRIPTION
        "This object value is same as Ifindex which interface index
        of a system."
    ::= { pf5000IfStatsEntry 1 }

pf5000IfStatsName OBJECT-TYPE
    SYNTAX  DisplayString
    ACCESS  read-only
    STATUS  mandatory
    DESCRIPTION
        "Interfaces name. Same as ifDescr."
    ::= { pf5000IfStatsEntry 2 }

pf5000IfStatsInMegaOctets OBJECT-TYPE
    SYNTAX  Counter
    ACCESS  read-only
    STATUS  mandatory
    DESCRIPTION
        "Number of octets that received on the interface. This value is
        displayed in mega-octets(M). Value of 0 through 999,999 are rounded
        down."
    ::= { pf5000IfStatsEntry 3 }

pf5000IfStatsInUcastMegaPkts OBJECT-TYPE
    SYNTAX  Counter
    ACCESS  read-only
    STATUS  mandatory
    DESCRIPTION
        "Number of subnetwork-unicast packets that received on the interface.
        This value is displayed in mega-packets(M).Value of 0 through 999,999
        are rounded down."
    ::= { pf5000IfStatsEntry 4 }

pf5000IfStatsInMulticastMegaPkts OBJECT-TYPE
    SYNTAX  Counter
    ACCESS  read-only
    STATUS  mandatory
    DESCRIPTION
        "Number of multicast mega-packets that received on the interface.
        this value is displayed in mega-packets(M).Value of 0 through 999,999
        are rounded down."
    ::= { pf5000IfStatsEntry 5 }


pf5000IfStatsInBroadcastMegaPkts OBJECT-TYPE
    SYNTAX  Counter
    ACCESS  read-only
    STATUS  mandatory
    DESCRIPTION
        "The number of non-unicast packets delivered to a higher-layer
        protocol. The value is displayed in mega-packets (M). Value of 0
        through 999,999 are rounded down. "
    ::= { pf5000IfStatsEntry 6 }

pf5000IfStatsOutMegaOctets OBJECT-TYPE
    SYNTAX  Counter
    ACCESS  read-only
    STATUS  mandatory
    DESCRIPTION
        "The total number of octets transmitted out of the interface.
        The value is displayed in mega-octets(M). Value of 0 through 999,999
        are rounded down."
    ::= { pf5000IfStatsEntry 7 }

pf5000IfStatsOutUcastMegaPkts OBJECT-TYPE
    SYNTAX  Counter
    ACCESS  read-only
    STATUS  mandatory
    DESCRIPTION
        "The total number of packets that higher-level protocols requested
        be transmitted to a subnetwork-unicast address.The value is displayed
        in mega packets(M). Value of 0 through 999,999 are rounded down."
    ::= { pf5000IfStatsEntry 8 }

pf5000IfStatsOutMulticastMegaPkts OBJECT-TYPE
    SYNTAX  Counter
    ACCESS  read-only
    STATUS  mandatory
    DESCRIPTION
        "Number of multicast packets that transmitted on the interface.
        This value is displayed in mega-packets(M). Value of 0 through
        999,999 are rounded down."
    ::= { pf5000IfStatsEntry 9 }

pf5000IfStatsOutBroadcastMegaPkts OBJECT-TYPE
    SYNTAX  Counter
    ACCESS  read-only
    STATUS  mandatory
    DESCRIPTION
        "Number of broadcast packets that transmitted on the interface.
        This value is displayed in mega-packets(M). Value of 0 through
        999,999 are rounded down. "
    ::= { pf5000IfStatsEntry 10 }

pf5000IfStatsHighSpeed OBJECT-TYPE
    SYNTAX  Counter
    ACCESS  read-only
    STATUS  mandatory
    DESCRIPTION
        "A circuit speed.This value is displayed in mega-bps[Mbps].
        Round off the 1,000,000bps. "
    ::= { pf5000IfStatsEntry 11 }

--  QoS interface statistics Variables

pf5000EtherTxQoSStatsTable OBJECT-TYPE
    SYNTAX  SEQUENCE OF Pf5000EtherTxQoSStatsEntry
    ACCESS  not-accessible
    STATUS  mandatory
    DESCRIPTION
        "A collection of QoS statistics kept for a particular
        Ethernet interface."
    ::= { pf5000EtherTxQoS 1 }

pf5000EtherTxQoSStatsEntry OBJECT-TYPE
    SYNTAX  Pf5000EtherTxQoSStatsEntry
    ACCESS  not-accessible
    STATUS  mandatory
    DESCRIPTION
        "An entry containing QoS statistics for a particular 
        Ethernet interface."
    INDEX { pf5000EtherTxQoSStatsIndex }
    ::= { pf5000EtherTxQoSStatsTable 1 }

    Pf5000EtherTxQoSStatsEntry ::=
        SEQUENCE {
            pf5000EtherTxQoSStatsIndex
                INTEGER,
            pf5000EtherTxQoSStatsMaxQnum
                INTEGER,
            pf5000EtherTxQoSStatsLimitQlen
                INTEGER,
            pf5000EtherTxQoSStatsTotalOutFrames
                Counter,
            pf5000EtherTxQoSStatsTotalOutBytesHigh
                Counter,
            pf5000EtherTxQoSStatsTotalOutBytesLow
                Counter,
            pf5000EtherTxQoSStatsTotalDiscardFrames
                Counter
        }

pf5000EtherTxQoSStatsIndex OBJECT-TYPE
    SYNTAX  INTEGER
    ACCESS  not-accessible
    STATUS  mandatory
    DESCRIPTION
        "Identified by a particular value of this
        index is same value of ifIndex.Its value ranges
        between 1 and the value of ifNumber."
    ::= { pf5000EtherTxQoSStatsEntry 1 }

pf5000EtherTxQoSStatsMaxQnum OBJECT-TYPE
    SYNTAX  INTEGER
    ACCESS  read-only
    STATUS  mandatory
    DESCRIPTION
        "Max length of queue for an ethernet interface."
    ::= { pf5000EtherTxQoSStatsEntry 2 }

pf5000EtherTxQoSStatsLimitQlen OBJECT-TYPE
    SYNTAX  INTEGER
    ACCESS  read-only
    STATUS  mandatory
    DESCRIPTION
        "The limit length of outband queue for an ethernet interface."
    ::= { pf5000EtherTxQoSStatsEntry 3 }

pf5000EtherTxQoSStatsTotalOutFrames OBJECT-TYPE
    SYNTAX  Counter
    ACCESS  read-only
    STATUS  mandatory
    DESCRIPTION
        "The total number of  packets transmitted out of the
        interface."
    ::= { pf5000EtherTxQoSStatsEntry 4 }

pf5000EtherTxQoSStatsTotalOutBytesHigh OBJECT-TYPE
    SYNTAX  Counter
    ACCESS  read-only
    STATUS  mandatory
    DESCRIPTION
        "The total number of octets transmitted out of the
        interface."
    ::= { pf5000EtherTxQoSStatsEntry 5 }

pf5000EtherTxQoSStatsTotalOutBytesLow OBJECT-TYPE
    SYNTAX  Counter
    ACCESS  read-only
    STATUS  mandatory
    DESCRIPTION
        "The total number of octets transmitted out of the
        interface."
    ::= { pf5000EtherTxQoSStatsEntry 6 }

pf5000EtherTxQoSStatsTotalDiscardFrames OBJECT-TYPE
    SYNTAX  Counter
    ACCESS  read-only
    STATUS  mandatory
    DESCRIPTION
        "The number of outbound packets which were chosen
        to be discarded ."
    ::= { pf5000EtherTxQoSStatsEntry 7 }

pf5000EtherTxQoSStatsQueueTable OBJECT-TYPE
    SYNTAX  SEQUENCE OF Pf5000EtherTxQoSStatsQueueEntry
    ACCESS  not-accessible
    STATUS  mandatory
    DESCRIPTION
        "A collection of priority queue statistics."
    ::= { pf5000EtherTxQoS 2 }

pf5000EtherTxQoSStatsQueueEntry OBJECT-TYPE
    SYNTAX  Pf5000EtherTxQoSStatsQueueEntry
    ACCESS  not-accessible
    STATUS  mandatory
    DESCRIPTION
        "A entry of priority queue statistics."
    INDEX { pf5000EtherTxQoSStatsQueueIndex,
            pf5000EtherTxQoSStatsQueueQueIndex }
    ::= { pf5000EtherTxQoSStatsQueueTable 1 }

    Pf5000EtherTxQoSStatsQueueEntry ::=
        SEQUENCE {
            pf5000EtherTxQoSStatsQueueIndex
                INTEGER,
            pf5000EtherTxQoSStatsQueueQueIndex
                INTEGER,
            pf5000EtherTxQoSStatsQueueQlen
                INTEGER,
            pf5000EtherTxQoSStatsQueueMaxQlen
                INTEGER,
            pf5000EtherTxQoSStatsQueueDiscardFramesClass1
                Counter64,
            pf5000EtherTxQoSStatsQueueDiscardFramesClass2
                Counter64,
            pf5000EtherTxQoSStatsQueueDiscardFramesClass3
                Counter64,
            pf5000EtherTxQoSStatsQueueDiscardFramesClass4
                Counter64
        }

pf5000EtherTxQoSStatsQueueIndex OBJECT-TYPE
    SYNTAX  INTEGER
    ACCESS  not-accessible
    STATUS  mandatory
    DESCRIPTION
        "Identified by a particular value of this
        index is same value of ifIndex.Its value ranges
        between 1 and the value of ifNumber."
    ::= { pf5000EtherTxQoSStatsQueueEntry 1 }

pf5000EtherTxQoSStatsQueueQueIndex OBJECT-TYPE
    SYNTAX  INTEGER
    ACCESS  not-accessible
    STATUS  mandatory
    DESCRIPTION
        "An index that uniquely identifies the particular
        queue.Its value ranges between 1 and the value of
        pf5000EtherTxQoSStatsMaxQnum."
    ::= { pf5000EtherTxQoSStatsQueueEntry 2 }

pf5000EtherTxQoSStatsQueueQlen OBJECT-TYPE
    SYNTAX  INTEGER
    ACCESS  read-only
    STATUS  mandatory
    DESCRIPTION
        "A length of outbound priority queue for a interface."
    ::= { pf5000EtherTxQoSStatsQueueEntry 3 }

pf5000EtherTxQoSStatsQueueMaxQlen OBJECT-TYPE
    SYNTAX  INTEGER
    ACCESS  read-only
    STATUS  mandatory
    DESCRIPTION
        "Max length of outband priority queue for a interface since
        system was up."
    ::= { pf5000EtherTxQoSStatsQueueEntry 4 }

pf5000EtherTxQoSStatsQueueDiscardFramesClass1 OBJECT-TYPE
    SYNTAX  Counter64
    ACCESS  read-only
    STATUS  mandatory
    DESCRIPTION
        "The number of discard frames in the discard class 
         1 of output priority queue."
    ::= { pf5000EtherTxQoSStatsQueueEntry 5 }

pf5000EtherTxQoSStatsQueueDiscardFramesClass2 OBJECT-TYPE
    SYNTAX  Counter64
    ACCESS  read-only
    STATUS  mandatory
    DESCRIPTION
        "The number of discard frames in the discard class 
         2 of output priority queue."
    ::= { pf5000EtherTxQoSStatsQueueEntry 6 }

pf5000EtherTxQoSStatsQueueDiscardFramesClass3 OBJECT-TYPE
    SYNTAX  Counter64
    ACCESS  read-only
    STATUS  mandatory
    DESCRIPTION
        "The number of discard frames in the discard class 
         3 of output priority queue."
    ::= { pf5000EtherTxQoSStatsQueueEntry 7 }

pf5000EtherTxQoSStatsQueueDiscardFramesClass4 OBJECT-TYPE
    SYNTAX  Counter64
    ACCESS  read-only
    STATUS  mandatory
    DESCRIPTION
        "The number of discard frames in the discard class 
         4 of output priority queue."
    ::= { pf5000EtherTxQoSStatsQueueEntry 8 }

--pf5000DHCP group Variables

pf5000DHCPAddrValue OBJECT-TYPE
    SYNTAX  INTEGER
    ACCESS  read-only
    STATUS  mandatory
    DESCRIPTION
        "The number of IP addresses which are available
        within this Router."
    ::= { pf5000DHCP 1 }

pf5000DHCPFreeAddrValue OBJECT-TYPE
    SYNTAX  INTEGER
    ACCESS  read-only
    STATUS  mandatory
    DESCRIPTION
        "The number of IP addresses which are available
        within this Router. May be expressed as either
        an absolute value."
    ::= { pf5000DHCP 2 }

--  pf5000Gsrp Group

pf5000GsrpGroupTable OBJECT-TYPE
        SYNTAX  SEQUENCE OF Pf5000GsrpGroupEntry
        ACCESS  not-accessible
        STATUS  mandatory
        DESCRIPTION
                "The table containing GSRP group information."
        ::= { pf5000Gsrp 1 }

pf5000GsrpGroupEntry OBJECT-TYPE
        SYNTAX  Pf5000GsrpGroupEntry
        ACCESS  not-accessible
        STATUS  mandatory
        DESCRIPTION
                "The list of GSRP group information."
    INDEX { pf5000GsrpGroupId }
        ::= { pf5000GsrpGroupTable 1 }

    Pf5000GsrpGroupEntry ::=
        SEQUENCE {
            pf5000GsrpGroupId             INTEGER,
            pf5000GsrpGroupRowStatus      RowStatus,
            pf5000GsrpMacAddress          MacAddress,
            pf5000GsrpAdvertiseHoldTime   INTEGER,
            pf5000GsrpAdvertiseInterval   INTEGER,
            pf5000GsrpSelectionPattern    INTEGER,
            pf5000GsrpLayer3Redundancy    INTEGER
        }

pf5000GsrpGroupId OBJECT-TYPE
    SYNTAX  INTEGER
    ACCESS  not-accessible
    STATUS  mandatory
    DESCRIPTION
        "GSRP group identifier."
    ::= { pf5000GsrpGroupEntry 1 }

pf5000GsrpGroupRowStatus OBJECT-TYPE
    SYNTAX  RowStatus
    ACCESS  read-only
    STATUS  mandatory
    DESCRIPTION
        "Valid/Invalid state of this entry. Valid(1) fixed"
    ::= { pf5000GsrpGroupEntry 2 }

pf5000GsrpMacAddress OBJECT-TYPE
    SYNTAX  MacAddress
    ACCESS  read-only
    STATUS  mandatory
    DESCRIPTION
        "The Media Access Control Address of this equipment."
    ::= { pf5000GsrpGroupEntry 3 }

pf5000GsrpAdvertiseHoldTime OBJECT-TYPE
    SYNTAX  INTEGER
    ACCESS  read-only
    STATUS  mandatory
    DESCRIPTION
        "Holding time of the Advertise frame (milli second)."
    ::= { pf5000GsrpGroupEntry 4 }

pf5000GsrpAdvertiseInterval OBJECT-TYPE
    SYNTAX  INTEGER
    ACCESS  read-only
    STATUS  mandatory
    DESCRIPTION
        "Interval between transmitting the Advertise frame (milli second)."
    ::= { pf5000GsrpGroupEntry 5 }

pf5000GsrpSelectionPattern OBJECT-TYPE
    SYNTAX  INTEGER {
        ports-Priority-MAC(1),
        priority-Ports-MAC(2)
    }
    ACCESS  read-only
    STATUS  mandatory
    DESCRIPTION
        "Master/Backup selection pattern. Ports-Priority-MAC(1)  Priority-Ports-MAC(2)"
    ::= { pf5000GsrpGroupEntry 6 }

pf5000GsrpLayer3Redundancy OBJECT-TYPE
    SYNTAX  INTEGER {
        off(1),
        on(2)
    }
    ACCESS  read-only
    STATUS  mandatory
    DESCRIPTION
        "The status of layer 3 redundancy-change."
    ::= { pf5000GsrpGroupEntry 7 }

pf5000GsrpVlanGroupTable OBJECT-TYPE
    SYNTAX  SEQUENCE OF Pf5000GsrpVlanGroupEntry
    ACCESS  not-accessible
    STATUS  mandatory
    DESCRIPTION
        "The table containing GSRP VLAN group information."
    ::= { pf5000Gsrp 2 }

pf5000GsrpVlanGroupEntry OBJECT-TYPE
    SYNTAX  Pf5000GsrpVlanGroupEntry
    ACCESS  not-accessible
    STATUS  mandatory
    DESCRIPTION
        "The list of GSRP VLAN group information."
    INDEX { pf5000GsrpGroupId, pf5000GsrpVlanGroupId }
    ::= { pf5000GsrpVlanGroupTable 1 }

    Pf5000GsrpVlanGroupEntry ::=
        SEQUENCE {
            pf5000GsrpVlanGroupId                  INTEGER,
            pf5000GsrpVlanGroupRowStatus           RowStatus,
            pf5000GsrpState                        INTEGER,
            pf5000GsrpPriority                     INTEGER,
            pf5000GsrpActivePorts                  INTEGER,
            pf5000GsrpTransitionToMasterCounts     INTEGER,
            pf5000GsrpTransitionFromMasterCounts   INTEGER,
            pf5000GsrpLastTransitionTime           TimeStamp,
            pf5000GsrpVirtualMacAddress            MacAddress
        }

pf5000GsrpVlanGroupId OBJECT-TYPE
    SYNTAX  INTEGER
    ACCESS  not-accessible
    STATUS  mandatory
    DESCRIPTION
        "GSRP VLAN group number(1~8)"
    ::= { pf5000GsrpVlanGroupEntry 1 }

pf5000GsrpVlanGroupRowStatus OBJECT-TYPE
    SYNTAX  RowStatus
    ACCESS  read-only
    STATUS  mandatory
    DESCRIPTION
        "Valid/Invalid state of this entry. Valid(1) fixed"
    ::= { pf5000GsrpVlanGroupEntry 2 }

pf5000GsrpState OBJECT-TYPE
    SYNTAX  INTEGER {
        backUp(1),
        backUp-Waiting(2),
        master(3),
        backUp-No-Neighbor(4),
        backUp-Lock(5)
    }
    ACCESS  read-only
    STATUS  mandatory
    DESCRIPTION
        "The state of GSRP group.."
    ::= { pf5000GsrpVlanGroupEntry 3 }

pf5000GsrpPriority OBJECT-TYPE
    SYNTAX  INTEGER
    ACCESS  read-only
    STATUS  mandatory
    DESCRIPTION
        "Configured priority."
    ::= { pf5000GsrpVlanGroupEntry 4 }

pf5000GsrpActivePorts OBJECT-TYPE
    SYNTAX  INTEGER
    ACCESS  read-only
    STATUS  mandatory
    DESCRIPTION
        "The number of port which is link-up  in monitored port."
    ::= { pf5000GsrpVlanGroupEntry 5 }

pf5000GsrpTransitionToMasterCounts OBJECT-TYPE
    SYNTAX  INTEGER
    ACCESS  read-only
    STATUS  mandatory
    DESCRIPTION
        "The number of times which shifted to the master state from the backup state."
    ::= { pf5000GsrpVlanGroupEntry 6 }

pf5000GsrpTransitionFromMasterCounts OBJECT-TYPE
    SYNTAX  INTEGER
    ACCESS  read-only
    STATUS  mandatory
    DESCRIPTION
        "The number of times which shifted to the backup state from the master state."
    ::= { pf5000GsrpVlanGroupEntry 7 }

pf5000GsrpLastTransitionTime OBJECT-TYPE
    SYNTAX  TimeStamp
    ACCESS  read-only
    STATUS  mandatory
    DESCRIPTION
        "The last time at which changed in the master state from the backup state or in the backup state from the master state."
    ::= { pf5000GsrpVlanGroupEntry 8 }

pf5000GsrpVirtualMacAddress OBJECT-TYPE
    SYNTAX  MacAddress
    ACCESS  read-only
    STATUS  mandatory
    DESCRIPTION
        "The virtual Media Access Control address of the GSRP VLAN group. If the status of layer 3 redundancy-change is off, return 00 00 00 00 00 00"
    ::= { pf5000GsrpVlanGroupEntry 9 }

pf5000GsrpNeighborGroupTable OBJECT-TYPE
    SYNTAX  SEQUENCE OF Pf5000GsrpNeighborGroupEntry
    ACCESS  not-accessible
    STATUS  mandatory
    DESCRIPTION
        "The table containing stores the GSRP group information on facing equipment."
    ::= { pf5000Gsrp 3 }

pf5000GsrpNeighborGroupEntry OBJECT-TYPE
    SYNTAX  Pf5000GsrpNeighborGroupEntry
    ACCESS  not-accessible
    STATUS  mandatory
    DESCRIPTION
        "The table containing stores the GSRP group information on facing equipment."
    INDEX { pf5000GsrpNeighborGroupId, pf5000GsrpNeighborMacAddress }
    ::= { pf5000GsrpNeighborGroupTable 1 }

    Pf5000GsrpNeighborGroupEntry ::=
        SEQUENCE {
            pf5000GsrpNeighborGroupId             INTEGER,
            pf5000GsrpNeighborMacAddress          MacAddress,
            pf5000GsrpNeighborAdvertiseHoldTime   INTEGER,
            pf5000GsrpNeighborAdvertiseInterval   INTEGER,
            pf5000GsrpNeighborSelectionPattern    INTEGER
        }

pf5000GsrpNeighborGroupId OBJECT-TYPE
    SYNTAX  INTEGER
    ACCESS  not-accessible
    STATUS  mandatory
    DESCRIPTION
        "The GSRP group identifier on the facing equipment."
    ::= { pf5000GsrpNeighborGroupEntry 1 }

pf5000GsrpNeighborMacAddress OBJECT-TYPE
    SYNTAX  MacAddress
    ACCESS  not-accessible
    STATUS  mandatory
    DESCRIPTION
        "The Media Access Control Address of the facing equipment."
    ::= { pf5000GsrpNeighborGroupEntry 2 }

pf5000GsrpNeighborAdvertiseHoldTime OBJECT-TYPE
    SYNTAX  INTEGER
    ACCESS  read-only
    STATUS  mandatory
    DESCRIPTION
        "Holding time of the Advertise frame on opposite equipment (milli second)."
    ::= { pf5000GsrpNeighborGroupEntry 3 }

pf5000GsrpNeighborAdvertiseInterval OBJECT-TYPE
    SYNTAX  INTEGER
    ACCESS  read-only
    STATUS  mandatory
    DESCRIPTION
        "Interval between transmitting the Advertise frame on the facing equipment (milli second)."
    ::= { pf5000GsrpNeighborGroupEntry 4 }

pf5000GsrpNeighborSelectionPattern OBJECT-TYPE
    SYNTAX  INTEGER {
        port-Priority-MAC(1),
        priority-Port-MAC(2)
    }
    ACCESS  read-only
    STATUS  mandatory
    DESCRIPTION
        "Master/Backup selection pattern on the facing equipment. Ports-Priority-MAC(1)  Priority-Ports-MAC(2)"
    ::= { pf5000GsrpNeighborGroupEntry 5 }

pf5000GsrpNeighborVlanGroupTable OBJECT-TYPE
    SYNTAX  SEQUENCE OF Pf5000GsrpNeighborVlanGroupEntry
    ACCESS  not-accessible
    STATUS  mandatory
    DESCRIPTION
        "The table containing the GSRP VLAN group information on facing equipment."
    ::= { pf5000Gsrp 4 }

pf5000GsrpNeighborVlanGroupEntry OBJECT-TYPE
    SYNTAX  Pf5000GsrpNeighborVlanGroupEntry
    ACCESS  not-accessible
    STATUS  mandatory
    DESCRIPTION
        "The table containing the GSRP VLAN group information on facing equipment."
    INDEX { pf5000GsrpNeighborGroupId, pf5000GsrpNeighborVlanGroupId, pf5000GsrpNeighborMacAddress }
        ::= { pf5000GsrpNeighborVlanGroupTable 1 }

    Pf5000GsrpNeighborVlanGroupEntry ::=
        SEQUENCE {
            pf5000GsrpNeighborVlanGroupId    INTEGER,
            pf5000GsrpNeighborState          INTEGER,
            pf5000GsrpNeighborPriority       INTEGER,
            pf5000GsrpNeighborActivePorts    INTEGER
        }

pf5000GsrpNeighborVlanGroupId OBJECT-TYPE
    SYNTAX  INTEGER
    ACCESS  not-accessible
    STATUS  mandatory
    DESCRIPTION
        "GSRP VLAN group number on the facing equipment (1~8)."
    ::= { pf5000GsrpNeighborVlanGroupEntry 1 }

pf5000GsrpNeighborState OBJECT-TYPE
    SYNTAX  INTEGER {
        backUp(1),
        backUp-Waiting(2),
        master(3),
        backUp-No-Neighbor(4),
        backUp-Lock(5)
    }
    ACCESS  not-accessible
    STATUS  mandatory
    DESCRIPTION
        "The state of GSRP group on the facing equipment."
    ::= { pf5000GsrpNeighborVlanGroupEntry 2 }

pf5000GsrpNeighborPriority OBJECT-TYPE
    SYNTAX  INTEGER
    ACCESS  read-only
    STATUS  mandatory
    DESCRIPTION
        "Configured priority on the facing equipment."
    ::= { pf5000GsrpNeighborVlanGroupEntry 3 }

pf5000GsrpNeighborActivePorts OBJECT-TYPE
    SYNTAX  INTEGER
    ACCESS  read-only
    STATUS  mandatory
    DESCRIPTION
        "The number of port which is link-up  in monitored port on the facing equipment."
    ::= { pf5000GsrpNeighborVlanGroupEntry 4 }

--  pf5000Fdb group

pf5000FdbCounterTable OBJECT-TYPE
    SYNTAX  SEQUENCE OF Pf5000FdbCounterEntry
    ACCESS  not-accessible
    STATUS  mandatory
    DESCRIPTION
        "The table of FDB information."
    ::= { pf5000Fdb 1 }

pf5000FdbCounterEntry OBJECT-TYPE
    SYNTAX  Pf5000FdbCounterEntry
    ACCESS  not-accessible
    STATUS  mandatory
    DESCRIPTION
        "The entry of FDB information."
    INDEX { pf5000FdbCounterNifIndex, pf5000FdbCounterLineIndex }
    ::= { pf5000FdbCounterTable 1 }

    Pf5000FdbCounterEntry ::=
        SEQUENCE {
            pf5000FdbCounterNifIndex    INTEGER,
            pf5000FdbCounterLineIndex   INTEGER,
            pf5000FdbCounterCounts      Counter32,
            pf5000FdbCounterType        INTEGER,
            pf5000FdbCounterLimits      Counter32
        }

pf5000FdbCounterNifIndex OBJECT-TYPE
    SYNTAX  INTEGER
    ACCESS  not-accessible
    STATUS  mandatory
    DESCRIPTION
        "Identified by a particular value of this index
        is same value of NIF.Its value ranges between 1
        and the value of pf5200NifBoardNumber."
    ::= { pf5000FdbCounterEntry 1 }

pf5000FdbCounterLineIndex OBJECT-TYPE
    SYNTAX  INTEGER
    ACCESS  not-accessible
    STATUS  mandatory
    DESCRIPTION
        "Identified by a particular value of this index
        is same value of Physical Line.Its value ranges
        between 1 and the value of pf5200NifLineNumber."
    ::= { pf5000FdbCounterEntry 2 }

pf5000FdbCounterCounts OBJECT-TYPE
    SYNTAX  Counter32
    ACCESS  read-only
    STATUS  mandatory
    DESCRIPTION
        "The number of FDB entries learned on the port."
    ::= { pf5000FdbCounterEntry 3 }

pf5000FdbCounterType OBJECT-TYPE
    SYNTAX  INTEGER    {
                unlimited(0),
                limited-and-Forward(1),
                limited-and-Discard(2)
            }
    ACCESS  read-only
    STATUS  mandatory
    DESCRIPTION
        "The type of FDB entries learning."
    ::= { pf5000FdbCounterEntry 4 }

pf5000FdbCounterLimits OBJECT-TYPE
    SYNTAX  Counter32
    ACCESS  read-only
    STATUS  mandatory
    DESCRIPTION
        "The maximum number of FDB entries that can be learned on the port."
    ::= { pf5000FdbCounterEntry 5 }

--  pf5000Vlan group

pf5000VBBaseTable OBJECT-TYPE
    SYNTAX  SEQUENCE OF Pf5000VBBaseEntry
    ACCESS  not-accessible
    STATUS  mandatory
    DESCRIPTION
        "An information table of dot1dBase by VLAN units."
    ::= { pf5000VlanBridgeBase 1 }

pf5000VBBaseEntry OBJECT-TYPE
    SYNTAX  Pf5000VBBaseEntry
    ACCESS  not-accessible
    STATUS  mandatory
    DESCRIPTION
        "An informatin entry of every VLAN ID of pf5000VBBaseTable."
    INDEX { pf5000VBBaseIndex }
    ::= { pf5000VBBaseTable 1 }

    Pf5000VBBaseEntry ::=
        SEQUENCE {
            pf5000VBBaseIndex                 VlanIndex,
            pf5000VBBaseBridgeAddress         MacAddress,
            pf5000VBBaseNumPorts              INTEGER,
            pf5000VBBaseType                  INTEGER,
            pf5000VBBaseVlanIfIndex           INTEGER,
            pf5000VBBaseVlanType              INTEGER,
            pf5000VBBaseVlanID                VlanIdOrZero,
            pf5000VBBaseAssociatedPrimaryVlan VlanIdOrZero,
            pf5000VBBaseIfStatus              INTEGER,
            pf5000VBBaseLastChange            TimeTicks,
            pf5000VBBasePrivateVlanType       INTEGER
        }

pf5000VBBaseIndex OBJECT-TYPE
    SYNTAX  VlanIndex
    ACCESS  read-only
    STATUS  mandatory
    DESCRIPTION
        "VLAN ID."
    ::= { pf5000VBBaseEntry 1 }

pf5000VBBaseBridgeAddress OBJECT-TYPE
    SYNTAX  MacAddress
    ACCESS  read-only
    STATUS  mandatory
    DESCRIPTION
        "MAC address of VLAN."
    ::= { pf5000VBBaseEntry 2 }

pf5000VBBaseNumPorts OBJECT-TYPE
    SYNTAX  INTEGER
    ACCESS  read-only
    STATUS  mandatory
    DESCRIPTION
        "The number of ports set at VLAN."
    ::= { pf5000VBBaseEntry 3 }

pf5000VBBaseType OBJECT-TYPE
    SYNTAX  INTEGER {
        unknown(1),
        transparent-only(2),
        sourceroute-only(3),
        srt(4)
    }
    ACCESS  read-only
    STATUS  mandatory
    DESCRIPTION
        "A bridging type VLAN may perform."
    ::= { pf5000VBBaseEntry 4 }

pf5000VBBaseVlanIfIndex OBJECT-TYPE
    SYNTAX  INTEGER
    ACCESS  read-only
    STATUS  mandatory
    DESCRIPTION
        "Value of ifIndex of interface of VLAN."
    ::= { pf5000VBBaseEntry 5 }

pf5000VBBaseVlanType OBJECT-TYPE
    SYNTAX  INTEGER {
        port-based(1),
        mac-based(2),
        protocol-based(3),
        ipsubnet-based(4)
    }
    ACCESS  read-only
    STATUS  mandatory
    DESCRIPTION
        "VLAN type."
    ::= { pf5000VBBaseEntry 6 }

pf5000VBBaseVlanID OBJECT-TYPE
    SYNTAX  VlanIdOrZero
    ACCESS  read-only
    STATUS  mandatory
    DESCRIPTION
        "Value of VID of VLAN-TAG corresponding VLAN."
    ::= { pf5000VBBaseEntry 7 }

pf5000VBBaseAssociatedPrimaryVlan OBJECT-TYPE
    SYNTAX  VlanIdOrZero
    ACCESS  read-only
    STATUS  mandatory
    DESCRIPTION
        "Returns VLAN ID of Primary VLAN when private VLAN is used and 
         the same VLAN is set at secondary VLAN."
    ::= { pf5000VBBaseEntry 8 }

pf5000VBBaseIfStatus OBJECT-TYPE
    SYNTAX  INTEGER {
        up(1),
        down(2)
    }
    ACCESS  read-only
    STATUS  mandatory
    DESCRIPTION
        "Status of interface against upper level protocol of VLAN."
    ::= { pf5000VBBaseEntry 9 }

pf5000VBBaseLastChange OBJECT-TYPE
    SYNTAX  TimeTicks
    ACCESS  read-only
    STATUS  mandatory
    DESCRIPTION
        "Value of sysUpTime which is set when VLAN topology changes."
    ::= { pf5000VBBaseEntry 10 }

pf5000VBBasePrivateVlanType OBJECT-TYPE
    SYNTAX  INTEGER {
        normal(1),
        primary(2),
        isolated(3),
        community(4)
    }
    ACCESS  read-only
    STATUS  mandatory
    DESCRIPTION
        "A private VLAN type of VLAN."
    ::= { pf5000VBBaseEntry 11 }

pf5000VBBasePortTable OBJECT-TYPE
    SYNTAX  SEQUENCE OF Pf5000VBBasePortEntry
    ACCESS  not-accessible
    STATUS  mandatory
    DESCRIPTION
        "An information table of dot1dBasePortTable by VLAN units."
    ::= { pf5000VlanBridgeBase 2 }

pf5000VBBasePortEntry OBJECT-TYPE
    SYNTAX  Pf5000VBBasePortEntry
    ACCESS  not-accessible
    STATUS  mandatory
    DESCRIPTION
        "A configuration entry of pf5000VBBaseTable."
    INDEX { pf5000VBBasePortIndex, pf5000VBBasePort }
    ::= { pf5000VBBasePortTable 1 }

    Pf5000VBBasePortEntry ::=
        SEQUENCE {
            pf5000VBBasePortIndex                  VlanIndex,
            pf5000VBBasePort                       INTEGER,
            pf5000VBBasePortIfIndex                INTEGER,
            pf5000VBBasePortCircuit                OBJECT IDENTIFIER,
            pf5000VBBasePortDelayExceededDiscards  Counter,
            pf5000VBBasePortMtuExceededDiscards    Counter,
            pf5000VBBasePortState                  INTEGER,
            pf5000VBBasePortTaggedState            INTEGER,
            pf5000VBBasePortTranslatedTagID        VlanIdOrZero
        }

pf5000VBBasePortIndex OBJECT-TYPE
    SYNTAX  VlanIndex
    ACCESS  read-only
    STATUS  mandatory
    DESCRIPTION
        "VLAN ID."
    ::= { pf5000VBBasePortEntry 1 }

pf5000VBBasePort OBJECT-TYPE
    SYNTAX  INTEGER
    ACCESS  read-only
    STATUS  mandatory
    DESCRIPTION
        "Port number of ports set at VLAN."
    ::= { pf5000VBBasePortEntry 2 }

pf5000VBBasePortIfIndex OBJECT-TYPE
    SYNTAX  INTEGER
    ACCESS  read-only
    STATUS  mandatory
    DESCRIPTION
        "Value of ifIndex corresponding ports set at VLAN."
    ::= { pf5000VBBasePortEntry 3 }

pf5000VBBasePortCircuit OBJECT-TYPE
    SYNTAX  OBJECT IDENTIFIER
    ACCESS  read-only
    STATUS  mandatory
    DESCRIPTION
        "Identifier which identifieds ports when VLAN ports
         have the same value as pf5000VBBasePortIfIndex."
    ::= { pf5000VBBasePortEntry 4 }

pf5000VBBasePortDelayExceededDiscards OBJECT-TYPE
    SYNTAX  Counter
    ACCESS  read-only
    STATUS  mandatory
    DESCRIPTION
        "Total number of discard frame caused by passing delay occured at VLAN ports."
    ::= { pf5000VBBasePortEntry 5 }

pf5000VBBasePortMtuExceededDiscards OBJECT-TYPE
    SYNTAX  Counter
    ACCESS  read-only
    STATUS  mandatory
    DESCRIPTION
        "Total number of discard frame caused by data over flow occured at VLAN ports."
    ::= { pf5000VBBasePortEntry 6 }

pf5000VBBasePortState OBJECT-TYPE
    SYNTAX  INTEGER {
        disabled(1),
        blocking(2),
        listening(3),
        learning(4),
        forwarding(5),
        broken(6),
        fix-forwarding(7)
    }
    ACCESS  read-only
    STATUS  mandatory
    DESCRIPTION
        "STP port status of port set at VLAN."
    ::= { pf5000VBBasePortEntry 7 }

pf5000VBBasePortTaggedState OBJECT-TYPE
    SYNTAX  INTEGER {
        untagged(1),
        tagged(2)
    }
    ACCESS  read-only
    STATUS  mandatory
    DESCRIPTION
        "Status of VLAN-TAG configuration of ports set at VLAN."
    ::= { pf5000VBBasePortEntry 8 }

pf5000VBBasePortTranslatedTagID OBJECT-TYPE
    SYNTAX  VlanIdOrZero
    ACCESS  read-only
    STATUS  mandatory
    DESCRIPTION
        "Translated ID of VLAN when TAG translation is set."
    ::= { pf5000VBBasePortEntry 9 }

pf5000VBStpTable OBJECT-TYPE
    SYNTAX  SEQUENCE OF Pf5000VBStpEntry
    ACCESS  not-accessible
    STATUS  mandatory
    DESCRIPTION
        "An information table of dot1dStpTable by VLAN units."
    ::= { pf5000VlanBridgeStp 1 }

pf5000VBStpEntry OBJECT-TYPE
    SYNTAX  Pf5000VBStpEntry
    ACCESS  not-accessible
    STATUS  mandatory
    DESCRIPTION
        "A configuration entry of pf5000VBStpTable."
    INDEX { pf5000VBStpIndex }
    ::= { pf5000VBStpTable 1 }

    Pf5000VBStpEntry ::=
        SEQUENCE {
            pf5000VBStpIndex                     VlanIndex,
            pf5000VBStpProtocolSpecification     INTEGER,
            pf5000VBStpPriority                  INTEGER,
            pf5000VBStpTimeSinceTopologyChange   TimeTicks,
            pf5000VBStpTopChanges                Counter,
            pf5000VBStpDesignatedRoot            BridgeId,
            pf5000VBStpRootCost                  INTEGER,
            pf5000VBStpRootPort                  INTEGER,
            pf5000VBStpMaxAge                    Timeout,
            pf5000VBStpHelloTime                 Timeout,
            pf5000VBStpHoldTime                  INTEGER,
            pf5000VBStpForwardDelay              Timeout,
            pf5000VBStpBridgeMaxAge              Timeout,
            pf5000VBStpBridgeHelloTime           Timeout,
            pf5000VBStpBridgeForwardDelay        Timeout
       }

pf5000VBStpIndex OBJECT-TYPE
    SYNTAX  VlanIndex
    ACCESS  read-only
    STATUS  mandatory
    DESCRIPTION
        "VLAN ID."
    ::= { pf5000VBStpEntry 1 }

pf5000VBStpProtocolSpecification OBJECT-TYPE
    SYNTAX  INTEGER {
        unknown(1),
        decLb100(2),
        ieee8021d(3),
        ieee8021w(4)
    }
    ACCESS  read-only
    STATUS  mandatory
    DESCRIPTION
        "A kind of spanning tree protocol by VLAN units."
    ::= { pf5000VBStpEntry 2 }

pf5000VBStpPriority OBJECT-TYPE
    SYNTAX  INTEGER
    ACCESS  read-only
    STATUS  mandatory
    DESCRIPTION
        "Priority value of spanning tree by VLAN units."
    ::= { pf5000VBStpEntry 3 }

pf5000VBStpTimeSinceTopologyChange OBJECT-TYPE
    SYNTAX  TimeTicks
    ACCESS  read-only
    STATUS  mandatory
    DESCRIPTION
        "Elapsed time since topology change of spanning tree by VLAN units."
    ::= { pf5000VBStpEntry 4 }

pf5000VBStpTopChanges OBJECT-TYPE
    SYNTAX  Counter
    ACCESS  read-only
    STATUS  mandatory
    DESCRIPTION
        "The number of times of topology changes of spanning tree by VLAN units."
    ::= { pf5000VBStpEntry 5 }

pf5000VBStpDesignatedRoot OBJECT-TYPE
    SYNTAX  BridgeId
    ACCESS  read-only
    STATUS  mandatory
    DESCRIPTION
        "Root bridge identifier of spanning tree by VLAN units."
    ::= { pf5000VBStpEntry 6 }

pf5000VBStpRootCost OBJECT-TYPE
    SYNTAX  INTEGER
    ACCESS  read-only
    STATUS  mandatory
    DESCRIPTION
        "Root path cost kept by spanning tree by VLAN units."
    ::= { pf5000VBStpEntry 7 }

pf5000VBStpRootPort OBJECT-TYPE
    SYNTAX  INTEGER
    ACCESS  read-only
    STATUS  mandatory
    DESCRIPTION
        "Root port value kept by spanning tree by VLAN units."
    ::= { pf5000VBStpEntry 8 }

pf5000VBStpMaxAge OBJECT-TYPE
    SYNTAX  Timeout
    ACCESS  read-only
    STATUS  mandatory
    DESCRIPTION
        "Maximum aging time kept by spanning tree by VLAN units."
    ::= { pf5000VBStpEntry 9 }

pf5000VBStpHelloTime OBJECT-TYPE
    SYNTAX  Timeout
    ACCESS  read-only
    STATUS  mandatory
    DESCRIPTION
        "Hello time kept by spanning tree by VLAN units."
    ::= { pf5000VBStpEntry 10 }

pf5000VBStpHoldTime OBJECT-TYPE
    SYNTAX  INTEGER
    ACCESS  read-only
    STATUS  mandatory
    DESCRIPTION
        "Hold time kept by spanning tree by VLAN units."
    ::= { pf5000VBStpEntry 11 }

pf5000VBStpForwardDelay OBJECT-TYPE
    SYNTAX  Timeout
    ACCESS  read-only
    STATUS  mandatory
    DESCRIPTION
        "Transfer delay time kept by spanning tree by VLAN units."
    ::= { pf5000VBStpEntry 12 }

pf5000VBStpBridgeMaxAge OBJECT-TYPE
    SYNTAX  Timeout
    ACCESS  read-only
    STATUS  mandatory
    DESCRIPTION
        "Maximum aging time used when spanning tree acts as a root bridge by VLAN units."
    ::= { pf5000VBStpEntry 13 }

pf5000VBStpBridgeHelloTime OBJECT-TYPE
    SYNTAX  Timeout
    ACCESS  read-only
    STATUS  mandatory
    DESCRIPTION
        "Hello time used when spanning tree act as a root bridge by VLAN units."
    ::= { pf5000VBStpEntry 14 }

pf5000VBStpBridgeForwardDelay OBJECT-TYPE
    SYNTAX  Timeout
    ACCESS  read-only
    STATUS  mandatory
    DESCRIPTION
        "Transfer delay time used when spanning tree act as a root bridge by VLAN units."
    ::= { pf5000VBStpEntry 15 }

pf5000VBStpPortTable OBJECT-TYPE
    SYNTAX  SEQUENCE OF Pf5000VBStpPortEntry
    ACCESS  not-accessible
    STATUS  mandatory
    DESCRIPTION
        "An information table of dot1dStpPortTable by VLAN units."
    ::= { pf5000VlanBridgeStp 2 }

pf5000VBStpPortEntry OBJECT-TYPE
    SYNTAX  Pf5000VBStpPortEntry
    ACCESS  not-accessible
    STATUS  mandatory
    DESCRIPTION
        "A configuration entry of pf5000VBStpPortTable."
    INDEX { pf5000VBStpPortIndex, pf5000VBStpPort }
    ::= { pf5000VBStpPortTable 1 }

    Pf5000VBStpPortEntry ::=
        SEQUENCE {
            pf5000VBStpPortIndex               VlanIndex,
            pf5000VBStpPort                    INTEGER,
            pf5000VBStpPortPriority            INTEGER,
            pf5000VBStpPortState               INTEGER,
            pf5000VBStpPortEnable              INTEGER,
            pf5000VBStpPortPathCost            INTEGER,
            pf5000VBStpPortDesignatedRoot      BridgeId,
            pf5000VBStpPortDesignatedCost      INTEGER,
            pf5000VBStpPortDesignatedBridge    BridgeId,
            pf5000VBStpPortDesignatedPort      OCTET STRING,
            pf5000VBStpPortForwardTransitions  Counter
     }

pf5000VBStpPortIndex OBJECT-TYPE
    SYNTAX  VlanIndex
    ACCESS  read-only
    STATUS  mandatory
    DESCRIPTION
        "VLAN ID."
    ::= { pf5000VBStpPortEntry 1 }

pf5000VBStpPort OBJECT-TYPE
    SYNTAX  INTEGER
    ACCESS  read-only
    STATUS  mandatory
    DESCRIPTION
        "Port number corresponding configuration entry."
    ::= { pf5000VBStpPortEntry 2 }

pf5000VBStpPortPriority OBJECT-TYPE
    SYNTAX  INTEGER
    ACCESS  read-only
    STATUS  mandatory
    DESCRIPTION
        "Priority of port by VLAN units."
    ::= { pf5000VBStpPortEntry 3 }

pf5000VBStpPortState OBJECT-TYPE
    SYNTAX  INTEGER {
        disabled(1),
        blocking(2),
        listening(3),
        learning(4),
        forwarding(5),
        broken(6)
    }
    ACCESS  read-only
    STATUS  mandatory
    DESCRIPTION
        "Present status of port by VLAN units."
    ::= { pf5000VBStpPortEntry 4 }

pf5000VBStpPortEnable OBJECT-TYPE
    SYNTAX  INTEGER {
        enabled(1),
        disabled(2)
    }
    ACCESS  read-only
    STATUS  mandatory
    DESCRIPTION
        "Value whether spanning tree is enabled or not at the port by VLAN units."
    ::= { pf5000VBStpPortEntry 5 }

pf5000VBStpPortPathCost OBJECT-TYPE
    SYNTAX  INTEGER
    ACCESS  read-only
    STATUS  mandatory
    DESCRIPTION
        "Path cost value of the port by VLAN units."
    ::= { pf5000VBStpPortEntry 6 }

pf5000VBStpPortDesignatedRoot OBJECT-TYPE
    SYNTAX  BridgeId
    ACCESS  read-only
    STATUS  mandatory
    DESCRIPTION
        "Value of root bridge identifier by VLAN units stored in BPDU from specified bridge."
    ::= { pf5000VBStpPortEntry 7 }

pf5000VBStpPortDesignatedCost OBJECT-TYPE
    SYNTAX  INTEGER
    ACCESS  read-only
    STATUS  mandatory
    DESCRIPTION
        "Path cost value of specified port connected to the port by VLAN units."
    ::= { pf5000VBStpPortEntry 8 }

pf5000VBStpPortDesignatedBridge OBJECT-TYPE
    SYNTAX  BridgeId
    ACCESS  read-only
    STATUS  mandatory
    DESCRIPTION
        "Bridge identifier of bridge which this port regards as specified bridge by VLAN units."
    ::= { pf5000VBStpPortEntry 9 }

pf5000VBStpPortDesignatedPort OBJECT-TYPE
    SYNTAX  OCTET STRING
    ACCESS  read-only
    STATUS  mandatory
    DESCRIPTION
        "Port identifier of specified bridge connected to this port by VLAN units."
    ::= { pf5000VBStpPortEntry 10 }

pf5000VBStpPortForwardTransitions OBJECT-TYPE
    SYNTAX  Counter
    ACCESS  read-only
    STATUS  mandatory
    DESCRIPTION
        "The number of times of changes from learning status into forwarding status."
    ::= { pf5000VBStpPortEntry 11 }

pf5000VBTpTable OBJECT-TYPE
    SYNTAX  SEQUENCE OF Pf5000VBTpEntry
    ACCESS  not-accessible
    STATUS  mandatory
    DESCRIPTION
        "A dot1dTp information table by VLAN units."
    ::= { pf5000VlanBridgeTp 1 }

pf5000VBTpEntry OBJECT-TYPE
    SYNTAX  Pf5000VBTpEntry
    ACCESS  not-accessible
    STATUS  mandatory
    DESCRIPTION
        "A configuration entry of pf5000VBTpTable."
    INDEX { pf5000VBTpIndex }
    ::= { pf5000VBTpTable 1 }

    Pf5000VBTpEntry ::=
        SEQUENCE {
            pf5000VBTpIndex                 VlanIndex,
            pf5000VBTpLearnedEntryDiscards  Counter,
            pf5000VBTpAgingTime             INTEGER
        }

pf5000VBTpIndex OBJECT-TYPE
    SYNTAX  VlanIndex
    ACCESS  read-only
    STATUS  mandatory
    DESCRIPTION
        "VLAN ID."
    ::= { pf5000VBTpEntry 1 }

pf5000VBTpLearnedEntryDiscards OBJECT-TYPE
    SYNTAX  Counter
    ACCESS  read-only
    STATUS  mandatory
    DESCRIPTION
        "The number of discarded entries because of lack of
         not-used domain in filtering data base."
    ::= { pf5000VBTpEntry 2 }

pf5000VBTpAgingTime OBJECT-TYPE
    SYNTAX  INTEGER
    ACCESS  read-only
    STATUS  mandatory
    DESCRIPTION
        "Time-out time to aging-out entry of filtering date base which is learned dynamically."
    ::= { pf5000VBTpEntry 3 }

pf5000VBTpFdbTable OBJECT-TYPE
    SYNTAX  SEQUENCE OF Pf5000VBTpFdbEntry
    ACCESS  not-accessible
    STATUS  mandatory
    DESCRIPTION
        "An information of dot1dTpFdbTable by VLAN units."
    ::= { pf5000VlanBridgeTp 2 }

pf5000VBTpFdbEntry OBJECT-TYPE
    SYNTAX  Pf5000VBTpFdbEntry
    ACCESS  not-accessible
    STATUS  mandatory
    DESCRIPTION
        "A configuration entry of pf5000VBTpFdbTable."
    INDEX { pf5000VBTpFdbIndex, pf5000VBTpFdbAddress }
    ::= { pf5000VBTpFdbTable 1 }

    Pf5000VBTpFdbEntry ::=
        SEQUENCE {
            pf5000VBTpFdbIndex     VlanIndex,
            pf5000VBTpFdbAddress   MacAddress,
            pf5000VBTpFdbPort      INTEGER,
            pf5000VBTpFdbStatus    INTEGER
        }

pf5000VBTpFdbIndex OBJECT-TYPE
    SYNTAX  VlanIndex
    ACCESS  read-only
    STATUS  mandatory
    DESCRIPTION
        "VLAN ID."
    ::= { pf5000VBTpFdbEntry 1 }

pf5000VBTpFdbAddress OBJECT-TYPE
    SYNTAX  MacAddress
    ACCESS  read-only
    STATUS  mandatory
    DESCRIPTION
        "Unicast MAC address of filtering data base entry."
    ::= { pf5000VBTpFdbEntry 2 }

pf5000VBTpFdbPort OBJECT-TYPE
    SYNTAX  INTEGER
    ACCESS  read-only
    STATUS  mandatory
    DESCRIPTION
        "Indicates that it hasn't learnt port number when
        port number 0 receives frame having MAC address
         as source address which pf5000VBTpFdbAddress indicates."
    ::= { pf5000VBTpFdbEntry 3 }

pf5000VBTpFdbStatus OBJECT-TYPE
    SYNTAX  INTEGER {
      other(1),
      invalid(2),
      learned(3),
      self(4),
      mgmt(5)
    }
    ACCESS  read-only
    STATUS  mandatory
    DESCRIPTION
        "Status of filtering data base."
    ::= { pf5000VBTpFdbEntry 4 }

pf5000VBTpPortTable OBJECT-TYPE
    SYNTAX  SEQUENCE OF Pf5000VBTpPortEntry
    ACCESS  not-accessible
    STATUS  mandatory
    DESCRIPTION
        "An information table of dot1dTpPortTable by VLAN units."
    ::= { pf5000VlanBridgeTp 3 }

pf5000VBTpPortEntry OBJECT-TYPE
    SYNTAX  Pf5000VBTpPortEntry
    ACCESS  not-accessible
    STATUS  mandatory
    DESCRIPTION
        "An information entry of pf5000VBTpPortTable of ports."
    INDEX { pf5000VBTpPortIndex, pf5000VBTpPort }
    ::= { pf5000VBTpPortTable 1 }

    Pf5000VBTpPortEntry ::=
        SEQUENCE {
            pf5000VBTpPortIndex        VlanIndex,
            pf5000VBTpPort             INTEGER,
            pf5000VBTpPortMaxInfo      INTEGER,
            pf5000VBTpPortInFrames     Counter,
            pf5000VBTpPortOutFrames    Counter,
            pf5000VBTpPortInDiscards   Counter
        }

pf5000VBTpPortIndex OBJECT-TYPE
    SYNTAX  VlanIndex
    ACCESS  read-only
    STATUS  mandatory
    DESCRIPTION
        "VLAN ID."
    ::= { pf5000VBTpPortEntry 1 }

pf5000VBTpPort OBJECT-TYPE
    SYNTAX  INTEGER
    ACCESS  read-only
    STATUS  mandatory
    DESCRIPTION
        "Port number that indicates which port management
         information in the entry corresponds."
    ::= { pf5000VBTpPortEntry 2 }

pf5000VBTpPortMaxInfo OBJECT-TYPE
    SYNTAX  INTEGER
    ACCESS  read-only
    STATUS  mandatory
    DESCRIPTION
        "Maximum INFO field size of the port by VLAN units."
    ::= { pf5000VBTpPortEntry 3 }

pf5000VBTpPortInFrames OBJECT-TYPE
    SYNTAX  Counter
    ACCESS  read-only
    STATUS  mandatory
    DESCRIPTION
        "The number of reception frame of the port by VLAN units."
    ::= { pf5000VBTpPortEntry 4 }

pf5000VBTpPortOutFrames OBJECT-TYPE
    SYNTAX  Counter
    ACCESS  read-only
    STATUS  mandatory
    DESCRIPTION
        "The number of sending frame of the port by VLAN units."
    ::= { pf5000VBTpPortEntry 5 }

pf5000VBTpPortInDiscards OBJECT-TYPE
    SYNTAX  Counter
    ACCESS  read-only
    STATUS  mandatory
    DESCRIPTION
        "The number of reception frame of the port by VLAN units."
    ::= { pf5000VBTpPortEntry 6 }

pf5000VBStaticTable OBJECT-TYPE
    SYNTAX  SEQUENCE OF Pf5000VBStaticEntry
    ACCESS  not-accessible
    STATUS  mandatory
    DESCRIPTION
        "An information table of dot1dStaticTable by VLAN units."
    ::= { pf5000VlanBridgeStatic 1 }

pf5000VBStaticEntry OBJECT-TYPE
    SYNTAX  Pf5000VBStaticEntry
    ACCESS  not-accessible
    STATUS  mandatory
    DESCRIPTION
        "A configuration entry of pf5000VBStaticTable."
    INDEX { pf5000VBStaticIndex, pf5000VBStaticAddress }
    ::= { pf5000VBStaticTable 1 }

    Pf5000VBStaticEntry ::=
        SEQUENCE {
            pf5000VBStaticIndex           VlanIndex,
            pf5000VBStaticAddress         MacAddress,
            pf5000VBStaticReceivePort     INTEGER,
            pf5000VBStaticAllowedToGoTo   OCTET STRING,
            pf5000VBStaticStatus          INTEGER
        }

pf5000VBStaticIndex OBJECT-TYPE
    SYNTAX  VlanIndex
    ACCESS  read-only
    STATUS  mandatory
    DESCRIPTION
        "VLAN ID."
    ::= { pf5000VBStaticEntry 1 }

pf5000VBStaticAddress OBJECT-TYPE
    SYNTAX  MacAddress
    ACCESS  read-only
    STATUS  mandatory
    DESCRIPTION
        "MAC address of eather unicast, group or broadcast."
    ::= { pf5000VBStaticEntry 2 }

pf5000VBStaticReceivePort OBJECT-TYPE
    SYNTAX  INTEGER
    ACCESS  read-only
    STATUS  mandatory
    DESCRIPTION
        "Reception port number which is applied the entry."
    ::= { pf5000VBStaticEntry 3 }

pf5000VBStaticAllowedToGoTo OBJECT-TYPE
    SYNTAX  OCTET STRING
    ACCESS  read-only
    STATUS  mandatory
    DESCRIPTION
        "Bit map of port indicating destination port when transfering
         frame whose destination is MAC address kept by this entry"
    ::= { pf5000VBStaticEntry 4 }

pf5000VBStaticStatus OBJECT-TYPE
    SYNTAX  INTEGER {
      other(1),
      invalid(2),
      permanent(3),
      deleteOnReset(4),
      deleteOnTimeout(5)
    }
    ACCESS  read-only
    STATUS  mandatory
    DESCRIPTION
        "Status of the entry."
    ::= { pf5000VBStaticEntry 5 }

pf5000VlanBridgeMaxVlans OBJECT-TYPE
    SYNTAX  VlanIndex
    ACCESS  read-only
    STATUS  mandatory
    DESCRIPTION
        "Maximum value of VLAN ID of this device."
    ::= { pf5000VlanBridge 101 }

pf5000VlanBridgeMaxSpans OBJECT-TYPE
    SYNTAX  VlanIndex
    ACCESS  read-only
    STATUS  mandatory
    DESCRIPTION
        "Maximum value of VLAN ID of VLAN which may operate
         spanning tree in this device."
    ::= { pf5000VlanBridge 102 }

pf5000VlanTagTranslationTable OBJECT-TYPE
    SYNTAX  SEQUENCE OF Pf5000VlanTagTranslationEntry
    ACCESS  not-accessible
    STATUS  mandatory
    DESCRIPTION
        "The information table about a Tag conversion function"
    ::= { pf5000VlanTagTranslation 1 }

pf5000VlanTagTranslationEntry OBJECT-TYPE
    SYNTAX  Pf5000VlanTagTranslationEntry
    ACCESS  not-accessible
    STATUS  mandatory
    DESCRIPTION
        "The entry of the information table about a Tag conversion function"
    INDEX { pf5000VlanTagTranslationVlanId,pf5000VlanTagTranslationTranslatedId }
    ::= { pf5000VlanTagTranslationTable 1 }

    Pf5000VlanTagTranslationEntry ::=
        SEQUENCE {
            pf5000VlanTagTranslationVlanId        INTEGER,
            pf5000VlanTagTranslationTranslatedId  INTEGER,
            pf5000VlanTagTranslationPorts         PortList
        }

pf5000VlanTagTranslationVlanId OBJECT-TYPE
    SYNTAX  INTEGER
    ACCESS  read-only
    STATUS  mandatory
    DESCRIPTION
        "VLAN ID which has set up the Tag conversion function"
    ::= { pf5000VlanTagTranslationEntry 1 }

pf5000VlanTagTranslationTranslatedId OBJECT-TYPE
    SYNTAX  INTEGER
    ACCESS  read-only
    STATUS  mandatory
    DESCRIPTION
        "Translated ID set up by the Tag conversion function"
    ::= { pf5000VlanTagTranslationEntry 2 }

pf5000VlanTagTranslationPorts OBJECT-TYPE
    SYNTAX  PortList
    ACCESS  read-only
    STATUS  mandatory
    DESCRIPTION
        "The port list which has set up the same Translated ID by the same VLAN by the Tag conversion function"
    ::= { pf5000VlanTagTranslationEntry 3 }

--  OADP Group

pf5000OadpGlobalActive  OBJECT-TYPE
    SYNTAX  TruthValue
    ACCESS  read-only
    STATUS  mandatory
    DESCRIPTION
        "Operation status of OADP function. Status set
         by enable or disable in Oadp configuration.
         enable : 1
         disable: 2"
    ::= { pf5000OadpGlobalInfo 1 }

pf5000OadpGlobalCdpActive  OBJECT-TYPE
    SYNTAX  TruthValue
    ACCESS  read-only
    STATUS  mandatory
    DESCRIPTION
        "Operation status of CDP reception function.
         Status whether cdp-listener is set or not in oadp configuration.
         cdp-listener           : 1
         cdp-listener is not set: 2"
    ::= { pf5000OadpGlobalInfo 2 }

pf5000OadpGlobalMessageInterval OBJECT-TYPE
    SYNTAX  INTEGER
    ACCESS  read-only
    STATUS  mandatory
    DESCRIPTION
        "Sending interval of OADP frame. The value of interval-time in oadp configuration."
    ::= { pf5000OadpGlobalInfo 3 }

pf5000OadpGlobalHoldTime OBJECT-TYPE
    SYNTAX  INTEGER
    ACCESS  read-only
    STATUS  mandatory
    DESCRIPTION
        "Neighbor divice's holding time of OADP frame which this device send.
         The value of hold-time in oadp configuration."
    ::= { pf5000OadpGlobalInfo 4 }

pf5000OadpGlobalCacheLastChange OBJECT-TYPE
    SYNTAX  TimeTicks
    ACCESS  read-only
    STATUS  mandatory
    DESCRIPTION
        "Value of sysUpTime which is set when pf5000OadpNeighborTable is updated."
    ::= { pf5000OadpGlobalInfo 5 }

pf5000OadpGlobalName OBJECT-TYPE
    SYNTAX  DisplayString
    ACCESS  read-only
    STATUS  mandatory
    DESCRIPTION
        "Device identifier."
    ::= { pf5000OadpGlobalInfo 6 }

pf5000OadpGlobalNameType OBJECT-TYPE
    SYNTAX  INTEGER {
      other(1),
      sysName(2),
      serialNumber(3),
      macaddress(4)
    }
    ACCESS  read-only
    STATUS  mandatory
    DESCRIPTION
        "Kind of pf5000OadpGlobalName."
    ::= { pf5000OadpGlobalInfo 7 }

pf5000OadpPortConfigTable OBJECT-TYPE
    SYNTAX  SEQUENCE OF Pf5000OadpPortConfigEntry
    ACCESS  not-accessible
    STATUS  mandatory
    DESCRIPTION
        "A table of OADP port information."
    ::= { pf5000OadpPortInfo 1 }

pf5000OadpPortConfigEntry OBJECT-TYPE
    SYNTAX  Pf5000OadpPortConfigEntry
    ACCESS  not-accessible
    STATUS  mandatory
    DESCRIPTION
        "An entry of OADP port information."
    INDEX { pf5000OadpPortConfigIfIndex }
    ::= { pf5000OadpPortConfigTable 1 }

    Pf5000OadpPortConfigEntry ::=
        SEQUENCE {
            pf5000OadpPortConfigIfIndex   InterfaceIndex,
            pf5000OadpPortConfigActive    TruthValue
        }

pf5000OadpPortConfigIfIndex OBJECT-TYPE
    SYNTAX  InterfaceIndex
    ACCESS  read-only
    STATUS  mandatory
    DESCRIPTION
        "Port identification index. The same value as ifIndex.
         This is only for physical ports and LA ports which are given
         ifIndex."
    ::= { pf5000OadpPortConfigEntry 1 }

pf5000OadpPortConfigActive OBJECT-TYPE
    SYNTAX  TruthValue
    ACCESS  read-only
    STATUS  mandatory
    DESCRIPTION
        "Status of specified port."
    ::= { pf5000OadpPortConfigEntry 2 }

pf5000OadpNeighborTable OBJECT-TYPE
    SYNTAX  SEQUENCE OF Pf5000OadpNeighborEntry
    ACCESS  not-accessible
    STATUS  mandatory
    DESCRIPTION
        "A table of OADP neighbor nodes."
    ::= { pf5000OadpNeighborInfo 1 }

pf5000OadpNeighborEntry OBJECT-TYPE
    SYNTAX  Pf5000OadpNeighborEntry
    ACCESS  not-accessible
    STATUS  mandatory
    DESCRIPTION
        "An entry of OADP neighbor nodes."
    INDEX { pf5000OadpIfIndex, pf5000OadpTagID, pf5000OadpNeighborIndex, pf5000OadpNeighborTagID }
    ::= { pf5000OadpNeighborTable 1 }

    Pf5000OadpNeighborEntry ::=
        SEQUENCE {
            pf5000OadpIfIndex
                InterfaceIndex,
            pf5000OadpTagID
                INTEGER,
            pf5000OadpNeighborIndex
                INTEGER,
            pf5000OadpNeighborTagID
                INTEGER,
            pf5000OadpNeighborVendorType
                INTEGER,
            pf5000OadpNeighborSNMPAgentAddressType
                INTEGER,
            pf5000OadpNeighborSNMPAgentAddress
                DisplayString,
            pf5000OadpNeighborDescr
                DisplayString,
            pf5000OadpNeighborDeviceID
                DisplayString,
            pf5000OadpNeighborSlotPort
                DisplayString,
            pf5000OadpNeighborIfIndex
                InterfaceIndex,
            pf5000OadpNeighborIfSpeed
                Gauge,
            pf5000OadpNeighborDeviceType
                DisplayString,
            pf5000OadpNeighborService
                OCTET STRING,
            pf5000OadpNeighborVTPMgmtDomain
                DisplayString,
            pf5000OadpNeighborNativeVLAN
                INTEGER,
            pf5000OadpNeighborDuplex
                INTEGER,
            pf5000OadpNeighborApplianceID
                Gauge,
            pf5000OadpNeighborVlanID
                Gauge,
            pf5000OadpNeighborPowerConsumption
                Gauge,
            pf5000OadpNeighborMTU
                Gauge,
            pf5000OadpNeighborSysName
                DisplayString,
            pf5000OadpNeighborSysObjectID
                OBJECT IDENTIFIER,
            pf5000OadpNeighborSecondarySNMPAgentAddressType
                INTEGER,
            pf5000OadpNeighborSecondarySNMPAgentAddress
                DisplayString,
            pf5000OadpNeighborPhysLocation
                DisplayString,
            pf5000OadpNeighborCacheLastChange
                TimeTicks,
            pf5000OadpNeighborIfHighSpeed
                Gauge
        }

pf5000OadpIfIndex OBJECT-TYPE
    SYNTAX  InterfaceIndex
    ACCESS  read-only
    STATUS  mandatory
    DESCRIPTION
        "ifIndex of reception interface."
    ::= { pf5000OadpNeighborEntry 1 }

pf5000OadpTagID OBJECT-TYPE
    SYNTAX  INTEGER
    ACCESS  read-only
    STATUS  mandatory
    DESCRIPTION
        "Tag ID of IEEE802.1Q which is attached MAC frame."
    ::= { pf5000OadpNeighborEntry 2 }

pf5000OadpNeighborIndex OBJECT-TYPE
    SYNTAX  INTEGER
    ACCESS  read-only
    STATUS  mandatory
    DESCRIPTION
        "Unique numeric which identifies neighbor nodes"
    ::= { pf5000OadpNeighborEntry 3 }

pf5000OadpNeighborTagID OBJECT-TYPE
    SYNTAX  INTEGER
    ACCESS  read-only
    STATUS  mandatory
    DESCRIPTION
        "Value set at TagID TLV in OADP PDU which is sent from neighbor node."
    ::= { pf5000OadpNeighborEntry 4 }

pf5000OadpNeighborVendorType OBJECT-TYPE
    SYNTAX  INTEGER {
        other(1),
        oadp(2),
        cdp(3)
    }
    ACCESS  read-only
    STATUS  mandatory
    DESCRIPTION
        "Protocol type used to find to neighbor nodes."
    ::= { pf5000OadpNeighborEntry 5 }

pf5000OadpNeighborSNMPAgentAddressType OBJECT-TYPE
    SYNTAX  INTEGER {
        ipv4(1),
        ipv6(20),
        other-notSupported(65535)
    }
    ACCESS  read-only
    STATUS  mandatory
    DESCRIPTION
        "A kind of agent address to get information by SNMP."
    ::= { pf5000OadpNeighborEntry 6 }

pf5000OadpNeighborSNMPAgentAddress OBJECT-TYPE
    SYNTAX  DisplayString
    ACCESS  read-only
    STATUS  mandatory
    DESCRIPTION
        "DisplayString formed information of agent address to get information by SNMP."
    ::= { pf5000OadpNeighborEntry 7 }

pf5000OadpNeighborDescr OBJECT-TYPE
    SYNTAX  DisplayString
    ACCESS  read-only
    STATUS  mandatory
    DESCRIPTION
        "String of sysDescr of neighbor node."
    ::= { pf5000OadpNeighborEntry 8 }

pf5000OadpNeighborDeviceID OBJECT-TYPE
    SYNTAX  DisplayString
    ACCESS  read-only
    STATUS  mandatory
    DESCRIPTION
        "Neighbor node's device identifier."
    ::= { pf5000OadpNeighborEntry 9 }

pf5000OadpNeighborSlotPort OBJECT-TYPE
    SYNTAX  DisplayString
    ACCESS  read-only
    STATUS  mandatory
    DESCRIPTION
        "Unique string which identifies neighbor's sending interface."
    ::= { pf5000OadpNeighborEntry 10 }

pf5000OadpNeighborIfIndex OBJECT-TYPE
    SYNTAX  InterfaceIndex
    ACCESS  read-only
    STATUS  mandatory
    DESCRIPTION
        "ifIndex of sending interface of neighbor node."
    ::= { pf5000OadpNeighborEntry 11 }

pf5000OadpNeighborIfSpeed OBJECT-TYPE
    SYNTAX  Gauge
    ACCESS  read-only
    STATUS  mandatory
    DESCRIPTION
        "ifSpeed of sending interface of neighbor node."
    ::= { pf5000OadpNeighborEntry 12 }

pf5000OadpNeighborDeviceType OBJECT-TYPE
    SYNTAX  DisplayString
    ACCESS  read-only
    STATUS  mandatory
    DESCRIPTION
        "Device name of neighbor node."
    ::= { pf5000OadpNeighborEntry 13 }

pf5000OadpNeighborService OBJECT-TYPE
    SYNTAX  OCTET STRING
    ACCESS  read-only
    STATUS  mandatory
    DESCRIPTION
        "Functions neighbor node can offer."
    ::= { pf5000OadpNeighborEntry 14 }

pf5000OadpNeighborVTPMgmtDomain OBJECT-TYPE
    SYNTAX  DisplayString
    ACCESS  read-only
    STATUS  mandatory
    DESCRIPTION
        "VTP Management Domain of sending interface of neighbor node."
    ::= { pf5000OadpNeighborEntry 15 }

pf5000OadpNeighborNativeVLAN OBJECT-TYPE
    SYNTAX  INTEGER
    ACCESS  read-only
    STATUS  mandatory
    DESCRIPTION
        "Native VLAN number of sending interface of neighbor node."
    ::= { pf5000OadpNeighborEntry 16 }

pf5000OadpNeighborDuplex OBJECT-TYPE
    SYNTAX  INTEGER {
        unknown(1),
        half(2),
        full(3)
    }
    ACCESS  read-only
    STATUS  mandatory
    DESCRIPTION
        "Duplex information of sending interface of neighbor node."
    ::= { pf5000OadpNeighborEntry 17 }

pf5000OadpNeighborApplianceID OBJECT-TYPE
    SYNTAX  Gauge
    ACCESS  read-only
    STATUS  mandatory
    DESCRIPTION
        "Appliance ID of neighbor node."
    ::= { pf5000OadpNeighborEntry 18 }

pf5000OadpNeighborVlanID OBJECT-TYPE
    SYNTAX  Gauge
    ACCESS  read-only
    STATUS  mandatory
    DESCRIPTION
        "VLAN ID for VoIP of neighbor node."
    ::= { pf5000OadpNeighborEntry 19 }

pf5000OadpNeighborPowerConsumption OBJECT-TYPE
    SYNTAX  Gauge
    ACCESS  read-only
    STATUS  mandatory
    DESCRIPTION
        "Electric power comsumption of neighbor node."
    ::= { pf5000OadpNeighborEntry 20 }

pf5000OadpNeighborMTU OBJECT-TYPE
    SYNTAX  Gauge
    ACCESS  read-only
    STATUS  mandatory
    DESCRIPTION
        "MTU of sending interface of neighbor node."
    ::= { pf5000OadpNeighborEntry 21 }

pf5000OadpNeighborSysName OBJECT-TYPE
    SYNTAX  DisplayString
    ACCESS  read-only
    STATUS  mandatory
    DESCRIPTION
        "sysName of neighbor node."
    ::= { pf5000OadpNeighborEntry 22 }

pf5000OadpNeighborSysObjectID OBJECT-TYPE
    SYNTAX  OBJECT IDENTIFIER
    ACCESS  read-only
    STATUS  mandatory
    DESCRIPTION
        "sysObjectID of neighbor node."
    ::= { pf5000OadpNeighborEntry 23 }

pf5000OadpNeighborSecondarySNMPAgentAddressType OBJECT-TYPE
    SYNTAX  INTEGER {
        ipv4(1),
        ipv6(20),
        other-notSupported(65535)
    }
    ACCESS  read-only
    STATUS  mandatory
    DESCRIPTION
        "A kind of agent secondary address to get information by SNMP."
    ::= { pf5000OadpNeighborEntry 24 }

pf5000OadpNeighborSecondarySNMPAgentAddress OBJECT-TYPE
    SYNTAX  DisplayString
    ACCESS  read-only
    STATUS  mandatory
    DESCRIPTION
        "DisplayString formed information of agent secondary address to get information by SNMP."
    ::= { pf5000OadpNeighborEntry 25 }

pf5000OadpNeighborPhysLocation OBJECT-TYPE
    SYNTAX  DisplayString
    ACCESS  read-only
    STATUS  mandatory
    DESCRIPTION
        "sysLocation of neighbor node."
    ::= { pf5000OadpNeighborEntry 26 }

pf5000OadpNeighborCacheLastChange OBJECT-TYPE
    SYNTAX  TimeTicks
    ACCESS  read-only
    STATUS  mandatory
    DESCRIPTION
        "Value of sysUpTime which is set when pf5000OadpNeighborEntry about neighbor node is updated."
    ::= { pf5000OadpNeighborEntry 27 }

pf5000OadpNeighborIfHighSpeed OBJECT-TYPE
    SYNTAX  Gauge
    ACCESS  read-only
    STATUS  mandatory
    DESCRIPTION
        "ifHighSpeed of sending interface of neighbor node."
    ::= { pf5000OadpNeighborEntry 28 }

--  pf5000Flow Group

pf5000AccessFilterStatsInTable OBJECT-TYPE
    SYNTAX  SEQUENCE OF Pf5000AccessFilterStatsInEntry
    ACCESS  not-accessible
    STATUS  mandatory
    DESCRIPTION
        "Table information on corresponding number of packets to flow detection condition 
        and operation information set by access list."
    ::= { pf5000AccessFilterStats 1 }

pf5000AccessFilterStatsInEntry OBJECT-TYPE
    SYNTAX  Pf5000AccessFilterStatsInEntry
    ACCESS  not-accessible
    STATUS  mandatory
    DESCRIPTION
        "Entry concerning corresponding number of packets to flow detection condition and 
        operation information set by access list."
    INDEX { pf5000AccessFilterStatsInifIndex,
            pf5000AccessFilterStatsInifIndexType,
            pf5000AccessFilterStatsInListIndex,
            pf5000AccessFilterStatsInSequenceNumber }
    ::= { pf5000AccessFilterStatsInTable 1 }

    Pf5000AccessFilterStatsInEntry ::=
        SEQUENCE {
            pf5000AccessFilterStatsInifIndex         INTEGER,
            pf5000AccessFilterStatsInifIndexType     INTEGER,
            pf5000AccessFilterStatsInListIndex       Unsigned32,
            pf5000AccessFilterStatsInSequenceNumber  Unsigned32,
            pf5000AccessFilterStatsInListName        DisplayString,
            pf5000AccessFilterStatsInMatchedPackets  Counter64
        }

pf5000AccessFilterStatsInifIndex OBJECT-TYPE
    SYNTAX  INTEGER
    ACCESS  not-accessible
    STATUS  mandatory
    DESCRIPTION
        "Index value in which entry of this table is identified."
    ::= { pf5000AccessFilterStatsInEntry 1 }

pf5000AccessFilterStatsInifIndexType OBJECT-TYPE
    SYNTAX  INTEGER
    ACCESS  not-accessible
    STATUS  mandatory
    DESCRIPTION
        "Indicates interface type. Physical port number : 1 Interface name : 2"
    ::= { pf5000AccessFilterStatsInEntry 2 }

pf5000AccessFilterStatsInListIndex OBJECT-TYPE
    SYNTAX  Unsigned32
    ACCESS  not-accessible
    STATUS  mandatory
    DESCRIPTION
        "Index value of access list that identifies entry of this table."
    ::= { pf5000AccessFilterStatsInEntry 3 }

pf5000AccessFilterStatsInSequenceNumber OBJECT-TYPE
    SYNTAX  Unsigned32
    ACCESS  not-accessible
    STATUS  mandatory
    DESCRIPTION
        "Sequence number of flow detection condition and operation information set to access list 
        number or access list name. "
    ::= { pf5000AccessFilterStatsInEntry 4 }

pf5000AccessFilterStatsInListName OBJECT-TYPE
    SYNTAX  DisplayString
    ACCESS  read-only
    STATUS  mandatory
    DESCRIPTION
        "Access list number or access list name corresponding to index of access list."
    ::= { pf5000AccessFilterStatsInEntry 5 }

pf5000AccessFilterStatsInMatchedPackets OBJECT-TYPE
    SYNTAX  Counter64
    ACCESS  read-only
    STATUS  mandatory
    DESCRIPTION
        "Corresponding number of packets to flow detection condition of access list. "
    ::= { pf5000AccessFilterStatsInEntry 6 }

pf5000AccessFilterStatsOutTable OBJECT-TYPE
    SYNTAX  SEQUENCE OF Pf5000AccessFilterStatsOutEntry
    ACCESS  not-accessible
    STATUS  mandatory
    DESCRIPTION
        "Table information on corresponding number of packets to flow detection condition 
        and operation information set by access list of Outbound."
    ::= { pf5000AccessFilterStats 2 }

pf5000AccessFilterStatsOutEntry OBJECT-TYPE
    SYNTAX  Pf5000AccessFilterStatsOutEntry
    ACCESS  not-accessible
    STATUS  mandatory
    DESCRIPTION
        "Entry concerning corresponding number of packets to flow detection condition and 
        operation information set by access list of Outbound."
    INDEX { pf5000AccessFilterStatsOutifIndex,
            pf5000AccessFilterStatsOutifIndexType,
            pf5000AccessFilterStatsOutListIndex,
            pf5000AccessFilterStatsOutSequenceNumber }
    ::= { pf5000AccessFilterStatsOutTable 1 }

    Pf5000AccessFilterStatsOutEntry ::=
        SEQUENCE {
            pf5000AccessFilterStatsOutifIndex         INTEGER,
            pf5000AccessFilterStatsOutifIndexType     INTEGER,
            pf5000AccessFilterStatsOutListIndex       Unsigned32,
            pf5000AccessFilterStatsOutSequenceNumber  Unsigned32,
            pf5000AccessFilterStatsOutListName        DisplayString,
            pf5000AccessFilterStatsOutMatchedPackets  Counter64
        }

pf5000AccessFilterStatsOutifIndex OBJECT-TYPE
    SYNTAX  INTEGER
    ACCESS  not-accessible
    STATUS  mandatory
    DESCRIPTION
        "Index value in which entry of this table is identified."
    ::= { pf5000AccessFilterStatsOutEntry 1 }

pf5000AccessFilterStatsOutifIndexType OBJECT-TYPE
    SYNTAX  INTEGER
    ACCESS  not-accessible
    STATUS  mandatory
    DESCRIPTION
        "Indicates interface type. Physical port number : 1 Interface name : 2"
    ::= { pf5000AccessFilterStatsOutEntry 2 }

pf5000AccessFilterStatsOutListIndex OBJECT-TYPE
    SYNTAX  Unsigned32
    ACCESS  not-accessible
    STATUS  mandatory
    DESCRIPTION
        "Index value of access list that identifies entry of this table."
    ::= { pf5000AccessFilterStatsOutEntry 3 }

pf5000AccessFilterStatsOutSequenceNumber OBJECT-TYPE
    SYNTAX  Unsigned32
    ACCESS  not-accessible
    STATUS  mandatory
    DESCRIPTION
        "Sequence number of flow detection condition and operation information set to access list 
        number or access list name. "
    ::= { pf5000AccessFilterStatsOutEntry 4 }

pf5000AccessFilterStatsOutListName OBJECT-TYPE
    SYNTAX  DisplayString
    ACCESS  read-only
    STATUS  mandatory
    DESCRIPTION
        "Access list number or access list name corresponding to index of access list."
    ::= { pf5000AccessFilterStatsOutEntry 5 }

pf5000AccessFilterStatsOutMatchedPackets OBJECT-TYPE
    SYNTAX  Counter64
    ACCESS  read-only
    STATUS  mandatory
    DESCRIPTION
        "Corresponding number of packets to flow detection condition of access list. "
    ::= { pf5000AccessFilterStatsOutEntry 6 }

pf5000QosFlowStatsInTable OBJECT-TYPE
    SYNTAX  SEQUENCE OF Pf5000QosFlowStatsInEntry
    ACCESS  not-accessible
    STATUS  mandatory
    DESCRIPTION
        "Table information on corresponding number of packets to QoS flow detection condition
        and operation information set in QoS flow list."
    ::= { pf5000QosFlowStats 1 }

pf5000QosFlowStatsInEntry OBJECT-TYPE
    SYNTAX  Pf5000QosFlowStatsInEntry
    ACCESS  not-accessible
    STATUS  mandatory
    DESCRIPTION
        "Entry concerning corresponding number of packets to QoS flow detection condition
        and operation information set in QoS Flower shop."
    INDEX { pf5000QosFlowStatsInifIndex,
            pf5000QosFlowStatsInifIndexType,
            pf5000QosFlowStatsInListIndex,
            pf5000QosFlowStatsInSequenceNumber }
        ::= { pf5000QosFlowStatsInTable 1 }

    Pf5000QosFlowStatsInEntry ::=
        SEQUENCE {
            pf5000QosFlowStatsInifIndex                 INTEGER,
            pf5000QosFlowStatsInifIndexType             INTEGER,
            pf5000QosFlowStatsInListIndex               Unsigned32,
            pf5000QosFlowStatsInSequenceNumber          Unsigned32,
            pf5000QosFlowStatsInListName                DisplayString,
            pf5000QosFlowStatsInMatchedPackets          Counter64,
            pf5000QosFlowStatsInMatchedPacketsMinUnder  Counter64,
            pf5000QosFlowStatsInMatchedPacketsMinOver   Counter64,
            pf5000QosFlowStatsInMatchedPacketsMaxUnder  Counter64,
            pf5000QosFlowStatsInMatchedPacketsMaxOver   Counter64
        }

pf5000QosFlowStatsInifIndex OBJECT-TYPE
    SYNTAX  INTEGER
    ACCESS  not-accessible
    STATUS  mandatory
    DESCRIPTION
        "Index value in which entry of this table is identified."
    ::= { pf5000QosFlowStatsInEntry 1 }

pf5000QosFlowStatsInifIndexType OBJECT-TYPE
    SYNTAX  INTEGER
    ACCESS  not-accessible
    STATUS  mandatory
    DESCRIPTION
        "Indicates interface type. Physical port number : 1 Interface name : 2"
    ::= { pf5000QosFlowStatsInEntry 2 }

pf5000QosFlowStatsInListIndex OBJECT-TYPE
    SYNTAX  Unsigned32
    ACCESS  not-accessible
    STATUS  mandatory
    DESCRIPTION
        "Index value of QoS Flow list where entry of this table is identified."
    ::= { pf5000QosFlowStatsInEntry 3 }

pf5000QosFlowStatsInSequenceNumber OBJECT-TYPE
    SYNTAX  Unsigned32
    ACCESS  not-accessible
    STATUS  mandatory
    DESCRIPTION
        "Sequence number of flow detection condition and operation information set to QoS 
        flow list name."
    ::= { pf5000QosFlowStatsInEntry 4 }

pf5000QosFlowStatsInListName OBJECT-TYPE
    SYNTAX  DisplayString
    ACCESS  read-only
    STATUS  mandatory
    DESCRIPTION
        "QoS flow list name corresponding to index of QoS flow list."
    ::= { pf5000QosFlowStatsInEntry 5 }

pf5000QosFlowStatsInMatchedPackets OBJECT-TYPE
    SYNTAX  Counter64
    ACCESS  read-only
    STATUS  mandatory
    DESCRIPTION
        "Corresponding number of packets to flow detection condition of QoS flow list."
    ::= { pf5000QosFlowStatsInEntry 6 }

pf5000QosFlowStatsInMatchedPacketsMinUnder OBJECT-TYPE
    SYNTAX  Counter64
    ACCESS  read-only
    STATUS  mandatory
    DESCRIPTION
        "Number of packets in which it agrees to flow detection condition of QoS flow 
        list and the lowest band watch is observed."
    ::= { pf5000QosFlowStatsInEntry 7 }

pf5000QosFlowStatsInMatchedPacketsMinOver OBJECT-TYPE
    SYNTAX  Counter64
    ACCESS  read-only
    STATUS  mandatory
    DESCRIPTION
        "Number of packets in which it agrees to flow detection condition of QoS flow 
        list and it violates the lowest band watch."
    ::= { pf5000QosFlowStatsInEntry 8 }

pf5000QosFlowStatsInMatchedPacketsMaxUnder OBJECT-TYPE
    SYNTAX  Counter64
    ACCESS  read-only
    STATUS  mandatory
    DESCRIPTION
        "Number of packets in which it agrees to flow detection condition of QoS flow 
        list and the maximum band control is observed."
    ::= { pf5000QosFlowStatsInEntry 9 }

pf5000QosFlowStatsInMatchedPacketsMaxOver OBJECT-TYPE
    SYNTAX  Counter64 
    ACCESS  read-only
    STATUS  mandatory
    DESCRIPTION
        "Number of packets in which it agrees to flow detection condition of QoS flow 
        list and it violates the maximum band control."
    ::= { pf5000QosFlowStatsInEntry 10 }

--  pf5000L2ldMIB Group

pf5000L2ldVersion OBJECT-TYPE
    SYNTAX  INTEGER
    ACCESS  read-only
    STATUS  mandatory
    DESCRIPTION
        "The version of L2 loop detection."
    ::= { pf5000L2ldGlobalInfo 1 }

pf5000L2ldLoopDetectionId OBJECT-TYPE
    SYNTAX  INTEGER
    ACCESS  read-only
    STATUS  mandatory
    DESCRIPTION
        "L2 loop detection ID."
    ::= { pf5000L2ldGlobalInfo 2 }

pf5000L2ldIntervalTime OBJECT-TYPE
    SYNTAX  INTEGER
    ACCESS  read-only
    STATUS  mandatory
    DESCRIPTION
        "Sending interval of L2 loop detection frame."
    ::= { pf5000L2ldGlobalInfo 3 }

pf5000L2ldOutputRate OBJECT-TYPE
    SYNTAX  INTEGER
    ACCESS  read-only
    STATUS  mandatory
    DESCRIPTION
        "Sending rate of L2 loop detection frame."
    ::= { pf5000L2ldGlobalInfo 4 }

pf5000L2ldThreshold OBJECT-TYPE
    SYNTAX  INTEGER
    ACCESS  read-only
    STATUS  mandatory
    DESCRIPTION
        "Detection counts until port is put into state of inactive."
    ::= { pf5000L2ldGlobalInfo 5 }

pf5000L2ldHoldTime OBJECT-TYPE
    SYNTAX  INTEGER
    ACCESS  read-only
    STATUS  mandatory
    DESCRIPTION
        "Hold time of detection counts."
    ::= { pf5000L2ldGlobalInfo 6 }

pf5000L2ldAutoRestoreTime OBJECT-TYPE
    SYNTAX  INTEGER
    ACCESS  read-only
    STATUS  mandatory
    DESCRIPTION
        "Time until port put into state of inactive is put into state of
        active by automatic operation."
    ::= { pf5000L2ldGlobalInfo 7 }

pf5000L2ldConfigurationVlanPortCounts OBJECT-TYPE
    SYNTAX  INTEGER
    ACCESS  read-only
    STATUS  mandatory
    DESCRIPTION
        "The number of VLAN ports set to send L2 loop detection frame."
    ::= { pf5000L2ldGlobalInfo 8 }

pf5000L2ldCapacityVlanPortCounts OBJECT-TYPE
    SYNTAX  INTEGER
    ACCESS  read-only
    STATUS  mandatory
    DESCRIPTION
        "The number of VLAN ports that can be sent by L2 loop detection
        frame sending rate."
    ::= { pf5000L2ldGlobalInfo 9 }

pf5000L2ldPortTable OBJECT-TYPE
    SYNTAX  SEQUENCE OF Pf5000L2ldPortEntry
    ACCESS  not-accessible
    STATUS  mandatory
    DESCRIPTION
        "The table containing port information on L2 loop detection."
    ::= { pf5000L2ld 2 }

pf5000L2ldPortEntry OBJECT-TYPE
    SYNTAX  Pf5000L2ldPortEntry
    ACCESS  not-accessible
    STATUS  mandatory
    DESCRIPTION
        "The entry of port information on L2 loop detection."
    INDEX { pf5000L2ldPortIndex,pf5000L2ldPortIfIndex }
    ::= { pf5000L2ldPortTable 1 }

    Pf5000L2ldPortEntry ::=
        SEQUENCE {
            pf5000L2ldPortIndex                     INTEGER,
            pf5000L2ldPortIfIndex                   INTEGER,
            pf5000L2ldPortStatus                    INTEGER,
            pf5000L2ldPortType                      INTEGER,
            pf5000L2ldPortDetectCount               INTEGER,
            pf5000L2ldPortAutoRestoringTimer        INTEGER,
            pf5000L2ldPortSourcePortIfindex         INTEGER,
            pf5000L2ldPortDestinationPortIfindex    INTEGER,
            pf5000L2ldPortSourceVlan                INTEGER,
            pf5000L2ldPortHCInFrames                Counter64,
            pf5000L2ldPortHCOutFrames               Counter64,
            pf5000L2ldPortHCInDiscards              Counter64,
            pf5000L2ldPortInactiveCount             INTEGER,
            pf5000L2ldPortLastInactiveTime          TimeStamp,
            pf5000L2ldPortLastInFramesTime          TimeStamp
        }

pf5000L2ldPortIndex OBJECT-TYPE
    SYNTAX  INTEGER
    ACCESS  read-only
    STATUS  mandatory
    DESCRIPTION
        "Index of L2 loop detection port."
    ::= { pf5000L2ldPortEntry 1 }

pf5000L2ldPortIfIndex OBJECT-TYPE
    SYNTAX  INTEGER
    ACCESS  read-only
    STATUS  mandatory
    DESCRIPTION
        "ifIndex of L2 loop detection port."
    ::= { pf5000L2ldPortEntry 2 }

pf5000L2ldPortStatus OBJECT-TYPE
    SYNTAX  INTEGER {
        up (1),
        down (2),
        loopDown (3)
    }
    ACCESS  read-only
    STATUS  mandatory
    DESCRIPTION
        "State of L2 loop detection port."
    ::= { pf5000L2ldPortEntry 3 }

pf5000L2ldPortType OBJECT-TYPE
    SYNTAX  INTEGER {
        trap (1),
        sendInact (2),
        send (3),
        upLink (4),
        exception (5)
    }
    ACCESS  read-only
    STATUS  mandatory
    DESCRIPTION
        "Type of L2 loop detection port."
    ::= { pf5000L2ldPortEntry 4 }

pf5000L2ldPortDetectCount OBJECT-TYPE
    SYNTAX  INTEGER
    ACCESS  read-only
    STATUS  mandatory
    DESCRIPTION
        "The number of L2 loop detection. The number in which
        L2 loop detection frame is received in hold time."
    ::= { pf5000L2ldPortEntry 5 }

pf5000L2ldPortAutoRestoringTimer OBJECT-TYPE
    SYNTAX  INTEGER
    ACCESS  read-only
    STATUS  mandatory
    DESCRIPTION
        "Time until restoring it automatically. The value is 0
        when port is active."
    ::= { pf5000L2ldPortEntry 6 }

pf5000L2ldPortSourcePortIfindex OBJECT-TYPE
    SYNTAX  INTEGER
    ACCESS  read-only
    STATUS  mandatory
    DESCRIPTION
        "ifIndex of port transmitted when L2 loop detection frame
        was received at the end."
    ::= { pf5000L2ldPortEntry 7 }

pf5000L2ldPortDestinationPortIfindex OBJECT-TYPE
    SYNTAX  INTEGER
    ACCESS  read-only
    STATUS  mandatory
    DESCRIPTION
        "ifIndex of port where L2 loop detection frame was
        received at the end."
    ::= { pf5000L2ldPortEntry 8 }

pf5000L2ldPortSourceVlan OBJECT-TYPE
    SYNTAX  INTEGER
    ACCESS  read-only
    STATUS  mandatory
    DESCRIPTION
        "VLAN ID when transmitting when L2 loop detection frame
        was received at the end."
    ::= { pf5000L2ldPortEntry 9 }

pf5000L2ldPortHCInFrames OBJECT-TYPE
    SYNTAX  Counter64
    ACCESS  read-only
    STATUS  mandatory
    DESCRIPTION
        "Number of receptions of L2 loop detection frames."
    ::= { pf5000L2ldPortEntry 10 }

pf5000L2ldPortHCOutFrames OBJECT-TYPE
    SYNTAX  Counter64
    ACCESS  read-only
    STATUS  mandatory
    DESCRIPTION
        "Number of transmissions of L2 loop detection frames."
    ::= { pf5000L2ldPortEntry 11 }

pf5000L2ldPortHCInDiscards OBJECT-TYPE
    SYNTAX  Counter64
    ACCESS  read-only
    STATUS  mandatory
    DESCRIPTION
        "Number of receptions of L2 loop detection discard frames."
    ::= { pf5000L2ldPortEntry 12 }

pf5000L2ldPortInactiveCount OBJECT-TYPE
    SYNTAX  INTEGER
    ACCESS  read-only
    STATUS  mandatory
    DESCRIPTION
        "The number of put into state of inactive."
    ::= { pf5000L2ldPortEntry 13 }

pf5000L2ldPortLastInactiveTime OBJECT-TYPE
    SYNTAX  TimeStamp
    ACCESS  read-only
    STATUS  mandatory
    DESCRIPTION
        "Time put into state of inactive at the end."
    ::= { pf5000L2ldPortEntry 14 }

pf5000L2ldPortLastInFramesTime OBJECT-TYPE
    SYNTAX  TimeStamp
    ACCESS  read-only
    STATUS  mandatory
    DESCRIPTION
        "Time to have received L2 loop detection frame at the end."
    ::= { pf5000L2ldPortEntry 15 }

--  OSPF General Variables

pf5000OspfGeneralTable OBJECT-TYPE
    SYNTAX  SEQUENCE OF Pf5000OspfGeneralEntry
    ACCESS  not-accessible
    STATUS  mandatory
    DESCRIPTION
        "The table of OSPF information."
    ::= { pf5000Ospf 1 }

pf5000OspfGeneralEntry OBJECT-TYPE
    SYNTAX  Pf5000OspfGeneralEntry
    ACCESS  not-accessible
    STATUS  mandatory
    DESCRIPTION
        "The entry of OSPF information."
    INDEX { pf5000OspfGeneralDomainNumber }
    ::= { pf5000OspfGeneralTable 1 }

    Pf5000OspfGeneralEntry ::=
        SEQUENCE {
            pf5000OspfGeneralDomainNumber   INTEGER,
            pf5000OspfRouterId              IpAddress,
            pf5000OspfAdminStat             INTEGER,
            pf5000OspfVersionNumber         INTEGER,
            pf5000OspfAreaBdrRtrStatus      INTEGER,
            pf5000OspfASBdrRtrStatus        INTEGER,
            pf5000OspfExternLsaCount        Gauge,
            pf5000OspfExternLsaCksumSum     INTEGER,
            pf5000OspfTOSSupport            INTEGER,
            pf5000OspfOriginateNewLsas      Counter,
            pf5000OspfRxNewLsas             Counter,
            pf5000OspfExtLsdbLimit          INTEGER,
            pf5000OspfMulticastExtensions   INTEGER
        }

pf5000OspfGeneralDomainNumber OBJECT-TYPE
    SYNTAX  INTEGER
    ACCESS  read-only
    STATUS  mandatory
    DESCRIPTION
        "Domain number in the Autonomous System."
    ::= { pf5000OspfGeneralEntry 1 }

pf5000OspfRouterId OBJECT-TYPE
    SYNTAX  IpAddress
    ACCESS  read-only
    STATUS  mandatory
    DESCRIPTION
        "A integer uniquely identifying the router
        in the Autonomous System."
    ::= { pf5000OspfGeneralEntry 2 }

pf5000OspfAdminStat OBJECT-TYPE
    SYNTAX  INTEGER {
        enabled(1),
        disabled(2)
    }
    ACCESS  read-only
    STATUS  mandatory
    DESCRIPTION
        "The  administrative  status  of  OSPF  in  the
        router.  "
    ::= { pf5000OspfGeneralEntry 3 }

pf5000OspfVersionNumber OBJECT-TYPE
    SYNTAX  INTEGER
    ACCESS  read-only
    STATUS  mandatory
    DESCRIPTION
        "The current version number of the OSPF  
        protocol is 2."
    ::= { pf5000OspfGeneralEntry 4 }

pf5000OspfAreaBdrRtrStatus OBJECT-TYPE
    SYNTAX  INTEGER {
        true(1),
        false(2)
    }
    ACCESS  read-only
    STATUS  mandatory
    DESCRIPTION
        "A flag to note whether this router is an  area
         border router."
    ::= { pf5000OspfGeneralEntry 5 }

pf5000OspfASBdrRtrStatus OBJECT-TYPE
    SYNTAX  INTEGER {
        true(1),
        false(2)
    }
    ACCESS  read-only
    STATUS  mandatory
    DESCRIPTION
        "A flag to note whether this router is  configured
        as an Autonomous System border router."
    ::= { pf5000OspfGeneralEntry 6 }

pf5000OspfExternLsaCount OBJECT-TYPE
    SYNTAX  Gauge
    ACCESS  read-only
    STATUS  mandatory
    DESCRIPTION
        "The number of external (LS type 5)  link-state
        advertisements in the link-state database."
    ::= { pf5000OspfGeneralEntry 7 }

pf5000OspfExternLsaCksumSum OBJECT-TYPE
    SYNTAX  INTEGER
    ACCESS  read-only
    STATUS  mandatory
    DESCRIPTION
        "The 32-bit unsigned sum of the LS checksums of
        the  external  link-state  advertisements  contained
        in the link-state  database."
    ::= { pf5000OspfGeneralEntry 8 }

pf5000OspfTOSSupport OBJECT-TYPE
    SYNTAX  INTEGER {
        true(1),
        false(2)
    }
    ACCESS  read-only
    STATUS  mandatory
    DESCRIPTION
        "The router's support for type-of-service routing.
         This value of false(2). "
    ::= { pf5000OspfGeneralEntry 9 }

pf5000OspfOriginateNewLsas OBJECT-TYPE
    SYNTAX  Counter
    ACCESS  read-only
    STATUS  mandatory
    DESCRIPTION
        "The number of  new  link-state  advertisements
        that have been originated. "
    ::= { pf5000OspfGeneralEntry 10 }

pf5000OspfRxNewLsas OBJECT-TYPE
    SYNTAX  Counter
    ACCESS  read-only
    STATUS  mandatory
    DESCRIPTION
        "The number of  link-state  advertisements  received
        determined  to  be  new instantiations."
    ::= { pf5000OspfGeneralEntry 11 }

pf5000OspfExtLsdbLimit OBJECT-TYPE
    SYNTAX  INTEGER
    ACCESS  read-only
    STATUS  mandatory
    DESCRIPTION
        "The maximum number of non-default AS-external-LSAs
        entries that can be stored in the link-state database.
        If the value is -1,  then there is no limit.
        This value is -1"
    ::= { pf5000OspfGeneralEntry 12 }

pf5000OspfMulticastExtensions OBJECT-TYPE
    SYNTAX  INTEGER
    ACCESS  read-only
    STATUS  mandatory
    DESCRIPTION
        "A Bit Mask indicating whether  the  router  is
        forwarding  IP  multicast  (Class  D) datagrams
        based on the algorithms defined in  the  Multicast
        Extensions to OSPF."
    ::= { pf5000OspfGeneralEntry 13 }

pf5000OspfAreaTable OBJECT-TYPE
    SYNTAX  SEQUENCE OF Pf5000OspfAreaEntry
    ACCESS  not-accessible
    STATUS  mandatory
    DESCRIPTION
        "The router's support for demand routing."
    ::= { pf5000Ospf 2 }

pf5000OspfAreaEntry OBJECT-TYPE
    SYNTAX  Pf5000OspfAreaEntry
    ACCESS  not-accessible
    STATUS  mandatory
    DESCRIPTION
        "This entry contain ospf area information."
    INDEX { pf5000OspfAreaDomainNumber, pf5000OspfAreaId }
    ::= { pf5000OspfAreaTable 1 }

    Pf5000OspfAreaEntry ::=
        SEQUENCE {
            pf5000OspfAreaDomainNumber  INTEGER,
            pf5000OspfAreaId            IpAddress,
            pf5000OspfAuthType          INTEGER,
            pf5000OspfImportAsExtern    INTEGER,
            pf5000OspfSpfRuns           Counter,
            pf5000OspfAreaBdrRtrCount   Gauge,
            pf5000OspfAsBdrRtrCount     Gauge,
            pf5000OspfAreaLsaCount      Gauge,
            pf5000OspfAreaLsaCksumSum   INTEGER,
            pf5000OspfAreaSummary       INTEGER,
            pf5000OspfAreaStatus        INTEGER
        }

pf5000OspfAreaDomainNumber OBJECT-TYPE
    SYNTAX  INTEGER
    ACCESS  read-only
    STATUS  mandatory
    DESCRIPTION
        "An uniquely identifying number of domain."
    ::= { pf5000OspfAreaEntry 1 }

pf5000OspfAreaId OBJECT-TYPE
    SYNTAX  IpAddress
    ACCESS  read-only
    STATUS  mandatory
    DESCRIPTION
        "A 32-bit integer uniquely identifying an area."
    ::= { pf5000OspfAreaEntry 2 }

pf5000OspfAuthType OBJECT-TYPE
    SYNTAX  INTEGER
            -- none(0),
            -- simplePassword (1),
            -- md5(2)
    ACCESS  read-only
    STATUS  mandatory
    DESCRIPTION
        "The authentication type specified for an area."
    ::= { pf5000OspfAreaEntry 3 }

pf5000OspfImportAsExtern OBJECT-TYPE
    SYNTAX  INTEGER { 
        importExternal (1),
        importNoExternal (2),
        importNssa (3)
    }
    ACCESS  read-only
    STATUS  mandatory
    DESCRIPTION
        "The area's support for importing  AS  external
        link- state advertisements."
    ::= { pf5000OspfAreaEntry 4 }

pf5000OspfSpfRuns OBJECT-TYPE
    SYNTAX  Counter
    ACCESS  read-only
    STATUS  mandatory
    DESCRIPTION
        "The number of times that the intra-area  route
        table  has  been  calculated  using this area's
        link-state database."
    ::= { pf5000OspfAreaEntry 5 }

pf5000OspfAreaBdrRtrCount OBJECT-TYPE
    SYNTAX  Gauge
    ACCESS  read-only
    STATUS  mandatory
    DESCRIPTION
        "The total number of area border routers reachable
        within this area."
    ::= { pf5000OspfAreaEntry 6 }

pf5000OspfAsBdrRtrCount OBJECT-TYPE
    SYNTAX  Gauge
    ACCESS  read-only
    STATUS  mandatory
    DESCRIPTION
        "The total number of AS area border routers reachable
        within this area."
    ::= { pf5000OspfAreaEntry 7 }

pf5000OspfAreaLsaCount OBJECT-TYPE
    SYNTAX  Gauge
    ACCESS  read-only
    STATUS  mandatory
    DESCRIPTION
        "The total number of LSA(link-state  advertisements) 
        in this area. Excluding AS External LSA's"
    ::= { pf5000OspfAreaEntry 8 }

pf5000OspfAreaLsaCksumSum OBJECT-TYPE
    SYNTAX  INTEGER
    ACCESS  read-only
    STATUS  mandatory
    DESCRIPTION
        "The sum of LSA's  LS  checksums  contained in this
        area's link-state database."
    ::= { pf5000OspfAreaEntry 9 }

pf5000OspfAreaSummary OBJECT-TYPE
    SYNTAX  INTEGER  {
        noAreaSummary (1),
        sendAreaSummary (2)
    }
    ACCESS  read-only
    STATUS  mandatory
    DESCRIPTION
        "he variable pf5000OspfAreaSummary controls the import
        of summary LSAs into stub areas. Value is only 
        sendAreaSummary(2)."
    ::= { pf5000OspfAreaEntry 10 }

pf5000OspfAreaStatus OBJECT-TYPE
    SYNTAX  INTEGER {
        active(1)
    }
    ACCESS  read-only
    STATUS  mandatory
    DESCRIPTION
        "This variable displays the status of  the  entry.
        Value is only valid(1)."
    ::= { pf5000OspfAreaEntry 11 }

pf5000OspfStubAreaTable OBJECT-TYPE
    SYNTAX  SEQUENCE OF Pf5000OspfStubAreaEntry
    ACCESS  not-accessible
    STATUS  mandatory
    DESCRIPTION
        "The set of metrics that will be advertised  by
        a default Area Border Router into a stub area."
    ::= { pf5000Ospf 3 }

pf5000OspfStubAreaEntry OBJECT-TYPE
    SYNTAX  Pf5000OspfStubAreaEntry
    ACCESS  not-accessible
    STATUS  mandatory
    DESCRIPTION
        "The metric for a given Type  of  Service  that
        will be advertised by a default Area Border Router 
        into a stub area."
    INDEX { pf5000OspfStubDomainNumber,
            pf5000OspfStubAreaId,
            pf5000OspfStubTOS }
    ::= { pf5000OspfStubAreaTable 1 }

    Pf5000OspfStubAreaEntry ::=
        SEQUENCE {
            pf5000OspfStubDomainNumber  INTEGER,
            pf5000OspfStubAreaId        IpAddress,
            pf5000OspfStubTOS           INTEGER,
            pf5000OspfStubMetric        INTEGER,
            pf5000OspfStubStatus        INTEGER,
            pf5000OspfStubMetricType    INTEGER
        }

pf5000OspfStubDomainNumber OBJECT-TYPE
    SYNTAX  INTEGER
    ACCESS  read-only
    STATUS  mandatory
    DESCRIPTION
        "The domain identifier for the Stub  Area."
    ::= { pf5000OspfStubAreaEntry 1 }

pf5000OspfStubAreaId OBJECT-TYPE
    SYNTAX  IpAddress
    ACCESS  read-only
    STATUS  mandatory
    DESCRIPTION
        "The identifier for the Stub  Area."
    ::= { pf5000OspfStubAreaEntry 2 }

pf5000OspfStubTOS OBJECT-TYPE
    SYNTAX  INTEGER
    ACCESS  read-only
    STATUS  mandatory
    DESCRIPTION
        "The Type of Service associated with the metric.
        Value is only 0."
    ::= { pf5000OspfStubAreaEntry 3 }

pf5000OspfStubMetric OBJECT-TYPE
    SYNTAX  INTEGER
    ACCESS  read-only
    STATUS  mandatory
    DESCRIPTION
        "The metric value applied at the indicated type
        of service."
    ::= { pf5000OspfStubAreaEntry 4 }

pf5000OspfStubStatus OBJECT-TYPE
    SYNTAX  INTEGER {
        active(1)
    }
    ACCESS  read-only
    STATUS  mandatory
    DESCRIPTION
        "This variable displays the status of the entry.
        This value is only valid(1)."
    ::= { pf5000OspfStubAreaEntry 5 }

pf5000OspfStubMetricType OBJECT-TYPE
    SYNTAX  INTEGER {
        ospfMetric(1),
        comparableCost(2),
        nonComparable(3)
    }
    ACCESS  read-only
    STATUS  mandatory
    DESCRIPTION
        "his variable displays the type of metric advertised
        as a default route."
    ::= { pf5000OspfStubAreaEntry 6 }

pf5000OspfLsdbTable OBJECT-TYPE
    SYNTAX  SEQUENCE OF Pf5000OspfLsdbEntry
    ACCESS  not-accessible
    STATUS  mandatory
    DESCRIPTION
        "The OSPF Process's Link State Database."
    ::= { pf5000Ospf 4 }

pf5000OspfLsdbEntry OBJECT-TYPE
    SYNTAX  Pf5000OspfLsdbEntry
    ACCESS  not-accessible
    STATUS  mandatory
    DESCRIPTION
         "A single Link State Advertisement."
    INDEX { pf5000OspfLsdbDomainNumber,
            pf5000OspfLsdbAreaId,
            pf5000OspfLsdbType,
            pf5000OspfLsdbLsid,
            pf5000OspfLsdbRouterId }
    ::= { pf5000OspfLsdbTable 1 }

    Pf5000OspfLsdbEntry ::=
        SEQUENCE {
            pf5000OspfLsdbDomainNumber   INTEGER,
            pf5000OspfLsdbAreaId         IpAddress,
            pf5000OspfLsdbType           INTEGER,
            pf5000OspfLsdbLsid           IpAddress,
            pf5000OspfLsdbRouterId       IpAddress,
            pf5000OspfLsdbSequence       INTEGER,
            pf5000OspfLsdbAge            INTEGER,
            pf5000OspfLsdbChecksum       INTEGER,
            pf5000OspfLsdbAdvertisement  OCTET STRING
        }

pf5000OspfLsdbDomainNumber OBJECT-TYPE
    SYNTAX  INTEGER
    ACCESS  read-only
    STATUS  mandatory
    DESCRIPTION
        "The identifier of the domain from  which
        the LSA was received."
    ::= { pf5000OspfLsdbEntry 1 }

pf5000OspfLsdbAreaId OBJECT-TYPE
    SYNTAX  IpAddress
    ACCESS  read-only
    STATUS  mandatory
    DESCRIPTION
        "The 32 bit identifier of the Area  from  which
        the LSA was received."
    ::= { pf5000OspfLsdbEntry 2 }

pf5000OspfLsdbType OBJECT-TYPE
    SYNTAX  INTEGER {
        routerLink (1),
        networkLink (2),
        summaryLink (3),
        asSummaryLink (4),
        asExternalLink (5), -- but see pf5000OspfExtLsdbTable
        multicastLink (6),
        nssaExternalLink (7)
    }
    ACCESS  read-only
    STATUS  mandatory
    DESCRIPTION
        "The type  of  the  link  state  advertisement."
    ::= { pf5000OspfLsdbEntry 3 }

pf5000OspfLsdbLsid OBJECT-TYPE
    SYNTAX  IpAddress
    ACCESS  read-only
    STATUS  mandatory
    DESCRIPTION
        "The Link State ID . It identifies the piece of the routing
        domain that is being described by the advertisement."
    ::= { pf5000OspfLsdbEntry 4 }

pf5000OspfLsdbRouterId OBJECT-TYPE
    SYNTAX  IpAddress
    ACCESS  read-only
    STATUS  mandatory
    DESCRIPTION
        "The number that uniquely identifies the originating 
        router in the Autonomous System."
    ::= { pf5000OspfLsdbEntry 5 }

pf5000OspfLsdbSequence OBJECT-TYPE
    SYNTAX  INTEGER
    ACCESS  read-only
    STATUS  mandatory
    DESCRIPTION
        "The sequence number field is a  signed  32-bit
        integer."
    ::= { pf5000OspfLsdbEntry 6 }

pf5000OspfLsdbAge OBJECT-TYPE
    SYNTAX  INTEGER
    ACCESS  read-only
    STATUS  mandatory
    DESCRIPTION
        "This the age of the link state adver-
        tisement in seconds."
    ::= { pf5000OspfLsdbEntry 7 }

pf5000OspfLsdbChecksum OBJECT-TYPE
    SYNTAX  INTEGER
    ACCESS  read-only
    STATUS  mandatory
    DESCRIPTION
        "This field is the  checksum  of  the  complete
        contents  of  the  advertisement, excepting the
        age field."
    ::= { pf5000OspfLsdbEntry 8 }

pf5000OspfLsdbAdvertisement OBJECT-TYPE
    SYNTAX  OCTET STRING
    ACCESS  read-only
    STATUS  mandatory
    DESCRIPTION
        "The entire Link State Advertisement, including
        its header."
    ::= { pf5000OspfLsdbEntry 9 }

pf5000OspfAreaRangeTable OBJECT-TYPE
    SYNTAX  SEQUENCE OF Pf5000OspfAreaRangeEntry
    ACCESS  not-accessible
    STATUS  mandatory
    DESCRIPTION
        "A range if IP addresses  specified  by  an  IP
        address/IP  network  mask  pair."
    ::= { pf5000Ospf 5 }

pf5000OspfAreaRangeEntry OBJECT-TYPE
    SYNTAX  Pf5000OspfAreaRangeEntry
    ACCESS  not-accessible
    STATUS  mandatory
    DESCRIPTION
        "A range if IP addresses specified by an IP
        address/IP network mask pair."
    INDEX { pf5000OspfAreaRangeDomainNumber, pf5000OspfAreaRangeAreaId,
            pf5000OspfAreaRangeNet }
    ::= { pf5000OspfAreaRangeTable 1 }

    Pf5000OspfAreaRangeEntry ::=
        SEQUENCE {
            pf5000OspfAreaRangeDomainNumber   INTEGER,
            pf5000OspfAreaRangeAreaId         IpAddress,
            pf5000OspfAreaRangeNet            IpAddress,
            pf5000OspfAreaRangeMask           IpAddress,
            pf5000OspfAreaRangeStatus         INTEGER,
            pf5000OspfAreaRangeEffect         INTEGER
        }

pf5000OspfAreaRangeDomainNumber OBJECT-TYPE
    SYNTAX  INTEGER
    ACCESS  read-only
    STATUS  mandatory
    DESCRIPTION
        "Domain number of the Area."
    ::= { pf5000OspfAreaRangeEntry 1 }

pf5000OspfAreaRangeAreaId OBJECT-TYPE
    SYNTAX  IpAddress
    ACCESS  read-only
    STATUS  mandatory
    DESCRIPTION
        "The Area the Address  Range  is  to  be  found
        within."
    ::= { pf5000OspfAreaRangeEntry 2 }

pf5000OspfAreaRangeNet OBJECT-TYPE
    SYNTAX  IpAddress
    ACCESS  read-only
    STATUS  mandatory
    DESCRIPTION
        "The IP Address of the Net or Subnet  indicated
        by the range."
    ::= { pf5000OspfAreaRangeEntry 3 }

pf5000OspfAreaRangeMask OBJECT-TYPE
    SYNTAX  IpAddress
    ACCESS  read-only
    STATUS  mandatory
    DESCRIPTION
        "The Subnet Mask that pertains to  the  Net  or
        Subnet."
    ::= { pf5000OspfAreaRangeEntry 4 }

pf5000OspfAreaRangeStatus OBJECT-TYPE
    SYNTAX  INTEGER {
        active(1),
        inactive(2)
    }
    ACCESS  read-only
    STATUS  mandatory
    DESCRIPTION
        "This variable displays the status of  the  entry.
        This value is only valid(1)."
    ::= { pf5000OspfAreaRangeEntry 5 }

pf5000OspfAreaRangeEffect OBJECT-TYPE
    SYNTAX  INTEGER {
        advertiseMatching (1),
        doNotAdvertiseMatching (2)
    }
    ACCESS  read-only
    STATUS  mandatory
    DESCRIPTION
        "Subnets subsumed by ranges either trigger  the
        advertisement  of the indicated summary (adver-
        tiseMatching), or result in  the  subnet's  not
        being advertised at all outside the area."
    ::= { pf5000OspfAreaRangeEntry 6 }

pf5000OspfIfTable OBJECT-TYPE
    SYNTAX  SEQUENCE OF Pf5000OspfIfEntry
    ACCESS  not-accessible
    STATUS  mandatory
    DESCRIPTION
        "The OSPF Interface Table describes the interfaces
        from the viewpoint of OSPF."
    ::= { pf5000Ospf 7 }

pf5000OspfIfEntry OBJECT-TYPE
    SYNTAX  Pf5000OspfIfEntry
    ACCESS  not-accessible
    STATUS  mandatory
    DESCRIPTION
        "The OSPF Interface Entry describes one  interface
        from the viewpoint of OSPF."
    INDEX { pf5000OspfIfDomainNumber, pf5000OspfIfIpAddress, pf5000OspfAddressLessIf }
    ::= { pf5000OspfIfTable 1 }

    Pf5000OspfIfEntry ::=
        SEQUENCE {
            pf5000OspfIfDomainNumber             INTEGER,
            pf5000OspfIfIpAddress                IpAddress,
            pf5000OspfAddressLessIf              INTEGER,
            pf5000OspfIfAreaId                   IpAddress,
            pf5000OspfIfType                     INTEGER,
            pf5000OspfIfAdminStat                INTEGER,
            pf5000OspfIfRtrPriority              INTEGER,
            pf5000OspfIfTransitDelay             INTEGER,
            pf5000OspfIfRetransInterval          INTEGER,
            pf5000OspfIfHelloInterval            INTEGER,
            pf5000OspfIfRtrDeadInterval          INTEGER,
            pf5000OspfIfPollInterval             INTEGER,
            pf5000OspfIfState                    INTEGER,
            pf5000OspfIfDesignatedRouter         IpAddress,
            pf5000OspfIfEvents                   Counter,
            pf5000OspfIfAuthKey                  OCTET STRING,
            pf5000OspfIfStatus                   INTEGER,
            pf5000OspfIfMulticastForwarding      INTEGER,
            pf5000OspfIfBackupDesignatedRouter   IpAddress
        }

pf5000OspfIfDomainNumber OBJECT-TYPE
    SYNTAX  INTEGER
    ACCESS  read-only
    STATUS  mandatory
    DESCRIPTION
        "The domain number of this OSPF interface."
    ::= { pf5000OspfIfEntry 1 }

pf5000OspfIfIpAddress OBJECT-TYPE
    SYNTAX  IpAddress
    ACCESS  read-only
    STATUS  mandatory
    DESCRIPTION
        "The IP address of this OSPF interface."
    ::= { pf5000OspfIfEntry 2 }

pf5000OspfAddressLessIf OBJECT-TYPE
    SYNTAX  INTEGER
    ACCESS  read-only
    STATUS  mandatory
    DESCRIPTION
        "For the purpose of easing  the  instancing  of
        addressed   and  addressless  interfaces;  This
        variable takes the value 0 on  interfaces  with
        IP  Addresses,  and  the corresponding value of
        ifIndex for interfaces having no IP Address."
    ::= { pf5000OspfIfEntry 3 }

pf5000OspfIfAreaId OBJECT-TYPE
    SYNTAX  IpAddress
    ACCESS  read-only
    STATUS  mandatory
    DESCRIPTION
        "A integer uniquely identifying the area to which 
        the interface connects."
    ::= { pf5000OspfIfEntry 4 }

pf5000OspfIfType OBJECT-TYPE
    SYNTAX  INTEGER {
        broadcast (1),
        nbma (2),
        pointToPoint (3),
        pointToMultipoint (5)
    }
    ACCESS  read-only
    STATUS  mandatory
    DESCRIPTION
        "The OSPF interface type."
    ::= { pf5000OspfIfEntry 5 }

pf5000OspfIfAdminStat OBJECT-TYPE
    SYNTAX  INTEGER { 
        enabled(1),
        disabled(2)
    }
    ACCESS  read-only
    STATUS  mandatory
    DESCRIPTION
        "The OSPF  interface's  administrative  status."
    ::= { pf5000OspfIfEntry 6 }

pf5000OspfIfRtrPriority OBJECT-TYPE
    SYNTAX  INTEGER
    ACCESS  read-only
    STATUS  mandatory
    DESCRIPTION
        "The priority of this interface."
    ::= { pf5000OspfIfEntry 7 }

pf5000OspfIfTransitDelay OBJECT-TYPE
    SYNTAX  INTEGER
    ACCESS  read-only
    STATUS  mandatory
    DESCRIPTION
        "The estimated number of seconds  it  takes  to
        transmit  a  link state update packet over this
        interface."
    ::= { pf5000OspfIfEntry 8 }

pf5000OspfIfRetransInterval OBJECT-TYPE
    SYNTAX  INTEGER
    ACCESS  read-only
    STATUS  mandatory
    DESCRIPTION
        "The number of seconds between link-state ad-
        vertisement retransmissions, for adjacencies
        belonging to this  interface."
    ::= { pf5000OspfIfEntry 9 }

pf5000OspfIfHelloInterval OBJECT-TYPE
    SYNTAX  INTEGER
    ACCESS  read-only
    STATUS  mandatory
    DESCRIPTION
        "The length of time, in  seconds,  between the
        Hello  packets that the router sends on the interface."
    ::= { pf5000OspfIfEntry 10 }

pf5000OspfIfRtrDeadInterval OBJECT-TYPE
    SYNTAX  INTEGER
    ACCESS  read-only
    STATUS  mandatory
    DESCRIPTION
        "The number of seconds that  a  router's  Hello
        packets  have  not been seen before it's neighbors 
        declare the router down."
    ::= { pf5000OspfIfEntry 11 }

pf5000OspfIfPollInterval OBJECT-TYPE
    SYNTAX  INTEGER
    ACCESS  read-only
    STATUS  mandatory
    DESCRIPTION
        "The larger time interval, in seconds,  between
        the  Hello  packets  sent  to  an inactive non-
        broadcast multi- access neighbor."
    ::= { pf5000OspfIfEntry 12 }

pf5000OspfIfState OBJECT-TYPE
    SYNTAX  INTEGER {
        down (1),
        loopback (2),
        waiting (3),
        pointToPoint (4),
        designatedRouter (5),
        backupDesignatedRouter (6),
        otherDesignatedRouter (7)
    }
    ACCESS  read-only
    STATUS  mandatory
    DESCRIPTION
        "The OSPF Interface State."
    ::= { pf5000OspfIfEntry 13 }

pf5000OspfIfDesignatedRouter OBJECT-TYPE
    SYNTAX  IpAddress
    ACCESS  read-only
    STATUS  mandatory
    DESCRIPTION
        "The IP Address of the Designated Router."
    ::= { pf5000OspfIfEntry 14 }

pf5000OspfIfEvents OBJECT-TYPE
    SYNTAX  Counter
    ACCESS  read-only
    STATUS  mandatory
    DESCRIPTION
        "The number of times this  OSPF  interface  has
        changed its state, or an error has occurred."
    ::= { pf5000OspfIfEntry 16 }

pf5000OspfIfAuthKey OBJECT-TYPE
    SYNTAX  OCTET STRING
    ACCESS  read-only
    STATUS  mandatory
    DESCRIPTION
        "The Authentication Key."
    ::= { pf5000OspfIfEntry 17 }

pf5000OspfIfStatus OBJECT-TYPE
    SYNTAX  INTEGER { 
        active(1),
        inactive(2)
    }
    ACCESS  read-only
    STATUS  mandatory
    DESCRIPTION
        "This variable displays the status of  the  entry.
        this value is only valid(1)."
    ::= { pf5000OspfIfEntry 18 }

pf5000OspfIfMulticastForwarding OBJECT-TYPE
    SYNTAX  INTEGER {
        blocked (1),       -- no multicast forwarding
        multicast (2),     -- using multicast address
        unicast (3)        -- to each OSPF neighbor
    }
    ACCESS  read-only
    STATUS  mandatory
    DESCRIPTION
        "The way multicasts should  forwarded  on  this
        interface;  not  forwarded,  forwarded  as data
        link multicasts, or forwarded as data link unicasts."
    ::= { pf5000OspfIfEntry 19 }

pf5000OspfIfBackupDesignatedRouter OBJECT-TYPE
    SYNTAX  IpAddress
    ACCESS  read-only
    STATUS  mandatory
    DESCRIPTION
        "The IP Address of the Backup Designated Router."
    ::= { pf5000OspfIfEntry 15 }

pf5000OspfIfMetricTable OBJECT-TYPE
    SYNTAX  SEQUENCE OF Pf5000OspfIfMetricEntry
    ACCESS  not-accessible
    STATUS  mandatory
    DESCRIPTION
        "The TOS metrics for a non-virtual interface identified
        by the interface index."
    ::= { pf5000Ospf 8 }

pf5000OspfIfMetricEntry OBJECT-TYPE
    SYNTAX  Pf5000OspfIfMetricEntry
    ACCESS  not-accessible
    STATUS  mandatory
    DESCRIPTION
        "A particular TOS metric for a non-virtual interface
        identified by the interface index."
    INDEX { pf5000OspfIfMetricDomainNumber,
            pf5000OspfIfMetricIpAddress,
            pf5000OspfIfMetricAddressLessIf,
            pf5000OspfIfMetricTOS }
    ::= { pf5000OspfIfMetricTable 1 }

    Pf5000OspfIfMetricEntry ::=
        SEQUENCE {
            pf5000OspfIfMetricDomainNumber    INTEGER,
            pf5000OspfIfMetricIpAddress       IpAddress,
            pf5000OspfIfMetricAddressLessIf   INTEGER,
            pf5000OspfIfMetricTOS             INTEGER,
            pf5000OspfIfMetricValue           INTEGER,
            pf5000OspfIfMetricStatus          INTEGER
        }

pf5000OspfIfMetricDomainNumber OBJECT-TYPE
    SYNTAX  INTEGER
    ACCESS  read-only
    STATUS  mandatory
    DESCRIPTION
        "The domain number of this OSPF interface."
    ::= { pf5000OspfIfMetricEntry 1 }

pf5000OspfIfMetricIpAddress OBJECT-TYPE
    SYNTAX  IpAddress
    ACCESS  read-only
    STATUS  mandatory
    DESCRIPTION
        "The IP address of this OSPF interface."
    ::= { pf5000OspfIfMetricEntry 2 }

pf5000OspfIfMetricAddressLessIf OBJECT-TYPE
    SYNTAX  INTEGER
    ACCESS  read-only
    STATUS  mandatory
    DESCRIPTION
        "For the purpose of easing  the  instancing  of
        addressed   and  addressless  interfaces;  This
        variable takes the value 0 on  interfaces  with
        IP  Addresses, and the value of ifIndex for in-
        terfaces having no IP Address."
    ::= { pf5000OspfIfMetricEntry 3 }

pf5000OspfIfMetricTOS OBJECT-TYPE
    SYNTAX  INTEGER
    ACCESS  read-only
    STATUS  mandatory
    DESCRIPTION
        "The type of service metric  being  referenced.
        this value is only 0."
    ::= { pf5000OspfIfMetricEntry 4 }

pf5000OspfIfMetricValue OBJECT-TYPE
    SYNTAX  INTEGER
    ACCESS  read-only
    STATUS  mandatory
    DESCRIPTION
        "The metric of using this type  of  service  on
        this interface."
    ::= { pf5000OspfIfMetricEntry 5 }

pf5000OspfIfMetricStatus OBJECT-TYPE
    SYNTAX  INTEGER {
        active(1)
    }
    ACCESS  read-only
    STATUS  mandatory
    DESCRIPTION
        "This variable displays the status of the entry.
        This entry status is only valid(1)."
    ::= { pf5000OspfIfMetricEntry 6 }

pf5000OspfVirtIfTable OBJECT-TYPE
    SYNTAX  SEQUENCE OF Pf5000OspfVirtIfEntry
    ACCESS  not-accessible
    STATUS  mandatory
    DESCRIPTION
        "Information about this router's virtual interfaces."
    ::= { pf5000Ospf 9 }

pf5000OspfVirtIfEntry OBJECT-TYPE
    SYNTAX  Pf5000OspfVirtIfEntry
    ACCESS  not-accessible
    STATUS  mandatory
    DESCRIPTION
        "Information about a single Virtual Interface."
    INDEX { pf5000OspfVirtIfDomainNumber,
            pf5000OspfVirtIfAreaId,
            pf5000OspfVirtIfNeighbor }
    ::= { pf5000OspfVirtIfTable 1 }

    Pf5000OspfVirtIfEntry ::=
        SEQUENCE {
            pf5000OspfVirtIfDomainNumber     INTEGER,
            pf5000OspfVirtIfAreaId           IpAddress,
            pf5000OspfVirtIfNeighbor         IpAddress,
            pf5000OspfVirtIfTransitDelay     INTEGER,
            pf5000OspfVirtIfRetransInterval  INTEGER,
            pf5000OspfVirtIfHelloInterval    INTEGER,
            pf5000OspfVirtIfRtrDeadInterval  INTEGER,
            pf5000OspfVirtIfState            INTEGER,
            pf5000OspfVirtIfEvents           Counter,
            pf5000OspfVirtIfAuthKey          OCTET STRING,
            pf5000OspfVirtIfStatus           INTEGER
        }

pf5000OspfVirtIfDomainNumber OBJECT-TYPE
    SYNTAX  INTEGER
    ACCESS  read-only
    STATUS  mandatory
    DESCRIPTION
        "The domain number for this  Virtual Interface"
    ::= { pf5000OspfVirtIfEntry 1 }

pf5000OspfVirtIfAreaId OBJECT-TYPE
    SYNTAX  IpAddress
    ACCESS  read-only
    STATUS  mandatory
    DESCRIPTION
        "The Transit Area that the Virtual Link traverses."
    ::= { pf5000OspfVirtIfEntry 2 }

pf5000OspfVirtIfNeighbor OBJECT-TYPE
    SYNTAX  IpAddress
    ACCESS  read-only
    STATUS  mandatory
    DESCRIPTION
        "The Router ID of the Virtual Neighbor."
    ::= { pf5000OspfVirtIfEntry 3 }

pf5000OspfVirtIfTransitDelay OBJECT-TYPE
    SYNTAX  INTEGER
    ACCESS  read-only
    STATUS  mandatory
    DESCRIPTION
        "The estimated number of seconds  it  takes  to
        transmit  a link- state update packet over this
        interface."
    ::= { pf5000OspfVirtIfEntry 4 }

pf5000OspfVirtIfRetransInterval OBJECT-TYPE
    SYNTAX  INTEGER
    ACCESS  read-only
    STATUS  mandatory
    DESCRIPTION
        "The number of seconds between link-state advertisement
        retransmissions, for adjacencies belonging to this
        interface."
    ::= { pf5000OspfVirtIfEntry 5 }

pf5000OspfVirtIfHelloInterval OBJECT-TYPE
    SYNTAX  INTEGER
    ACCESS  read-only
    STATUS  mandatory
    DESCRIPTION
        "The length of time, in  seconds, between the
        Hello  packets that the router sends on the in-
        terface. "
    ::= { pf5000OspfVirtIfEntry 6 }

pf5000OspfVirtIfRtrDeadInterval OBJECT-TYPE
    SYNTAX  INTEGER
    ACCESS  read-only
    STATUS  mandatory
    DESCRIPTION
        "The number of seconds that  a  router's  Hello
        packets  have  not been seen before it's neighbors
        declare the router down."
    ::= { pf5000OspfVirtIfEntry 7 }

pf5000OspfVirtIfState OBJECT-TYPE
    SYNTAX  INTEGER {
        down (1),            -- these use the same encoding
        pointToPoint (4)     -- as the pf5000OspfIfTable
    }
    ACCESS  read-only
    STATUS  mandatory
    DESCRIPTION
        "OSPF virtual interface states."
    ::= { pf5000OspfVirtIfEntry 8 }

pf5000OspfVirtIfEvents OBJECT-TYPE
    SYNTAX  Counter
    ACCESS  read-only
    STATUS  mandatory
    DESCRIPTION
        "The number of state changes or error events on
        this Virtual Link"
    ::= { pf5000OspfVirtIfEntry 9 }

pf5000OspfVirtIfAuthKey OBJECT-TYPE
    SYNTAX  OCTET STRING
    ACCESS  read-only
    STATUS  mandatory
    DESCRIPTION
        "Authentication key of this interface."
    ::= { pf5000OspfVirtIfEntry 10 }

pf5000OspfVirtIfStatus OBJECT-TYPE
    SYNTAX  INTEGER { 
        active(1),
        inactive(2)
    }
    ACCESS  read-only
    STATUS  mandatory
    DESCRIPTION
        "This variable displays the status of  the  entry.
        This entry is only valid(1)."
    ::= { pf5000OspfVirtIfEntry 11 }

pf5000OspfNbrTable OBJECT-TYPE
    SYNTAX  SEQUENCE OF Pf5000OspfNbrEntry
    ACCESS  not-accessible
    STATUS  mandatory
    DESCRIPTION
        "A table of non-virtual neighbor information."
    ::= { pf5000Ospf 10 }

pf5000OspfNbrEntry OBJECT-TYPE
    SYNTAX  Pf5000OspfNbrEntry
    ACCESS  not-accessible
    STATUS  mandatory
    DESCRIPTION
        "The information regarding a single neighbor."
    INDEX { pf5000OspfNbrDomainNumber, pf5000OspfNbrIpAddr, pf5000OspfNbrAddressLessIndex }
    ::= { pf5000OspfNbrTable 1 }

    Pf5000OspfNbrEntry ::=
        SEQUENCE {
            pf5000OspfNbrDomainNumber       INTEGER,
            pf5000OspfNbrIpAddr             IpAddress,
            pf5000OspfNbrAddressLessIndex   INTEGER,
            pf5000OspfNbrRtrId              IpAddress,
            pf5000OspfNbrOptions            INTEGER,
            pf5000OspfNbrPriority           INTEGER,
            pf5000OspfNbrState              INTEGER,
            pf5000OspfNbrEvents             Counter,
            pf5000OspfNbrLsRetransQLen      Gauge,
            pf5000OspfNbmaNbrStatus         INTEGER,
            pf5000OspfNbmaNbrPermanence     INTEGER
        }

pf5000OspfNbrDomainNumber OBJECT-TYPE
    SYNTAX  INTEGER
    ACCESS  read-only
    STATUS  mandatory
    DESCRIPTION
        "OSPF domain number of this neighbor."
    ::= { pf5000OspfNbrEntry 1 }

pf5000OspfNbrIpAddr OBJECT-TYPE
    SYNTAX  IpAddress
    ACCESS  read-only
    STATUS  mandatory
    DESCRIPTION
        "The IP address this neighbor is using  in  its
        IP  Source  Address."
    ::= { pf5000OspfNbrEntry 2 }

pf5000OspfNbrAddressLessIndex OBJECT-TYPE
    SYNTAX  INTEGER
    ACCESS  read-only
    STATUS  mandatory
    DESCRIPTION
        "On an interface having an  IP  Address,  zero.
        On  addressless  interfaces,  the corresponding
        value of ifIndex in the Internet Standard  MIB."
    ::= { pf5000OspfNbrEntry 3 }

pf5000OspfNbrRtrId OBJECT-TYPE
    SYNTAX  IpAddress
    ACCESS  read-only
    STATUS  mandatory
    DESCRIPTION
        "The integer uniquely identifying the neighboring
        router in the Autonomous System."
    ::= { pf5000OspfNbrEntry 4 }

pf5000OspfNbrOptions OBJECT-TYPE
    SYNTAX  INTEGER
    ACCESS  read-only
    STATUS  mandatory
    DESCRIPTION
        "A Bit Mask corresponding to the neighbor's op-
         tions field.

         Bit 0, if set, indicates that the  system  will
         operate  on  Type of Service metrics other than
         TOS 0.  If zero, the neighbor will  ignore  all
         metrics except the TOS 0 metric.

         Bit 1, if set, indicates  that  the  associated
         area  accepts and operates on external informa-
         tion; if zero, it is a stub area.

         Bit 2, if set, indicates that the system is ca-
         pable  of routing IP Multicast datagrams; i.e.,
         that it implements the Multicast Extensions  to
         OSPF.

         Bit 3, if set, indicates  that  the  associated
         area  is  an  NSSA.  These areas are capable of
         carrying type 7 external advertisements,  which
         are  translated into type 5 external advertise-
         ments at NSSA borders."
    ::= { pf5000OspfNbrEntry 5 }

pf5000OspfNbrPriority OBJECT-TYPE
    SYNTAX  INTEGER
    ACCESS  read-only
    STATUS  mandatory
    DESCRIPTION
        "The priority of this neighbor."
    ::= { pf5000OspfNbrEntry 6 }

pf5000OspfNbrState OBJECT-TYPE
    SYNTAX  INTEGER {
        down (1),
        attempt (2),
        init (3),
        twoWay (4),
        exchangeStart (5),
        exchange (6),
        loading (7),
        full (8)
    }
    ACCESS  read-only
    STATUS  mandatory
    DESCRIPTION
        "The State of the relationship with this Neighbor."
    ::= { pf5000OspfNbrEntry 7 }

pf5000OspfNbrEvents OBJECT-TYPE
    SYNTAX  Counter
    ACCESS  read-only
    STATUS  mandatory
    DESCRIPTION
        "The number of times this neighbor relationship
        has changed state, or an error has occurred."
    ::= { pf5000OspfNbrEntry 8 }

pf5000OspfNbrLsRetransQLen OBJECT-TYPE
    SYNTAX  Gauge
    ACCESS  read-only
    STATUS  mandatory
    DESCRIPTION
        "The current length of the retransmission queue."
    ::= { pf5000OspfNbrEntry 9 }

pf5000OspfNbmaNbrStatus OBJECT-TYPE
    SYNTAX  INTEGER {
        active(1)
    }
    ACCESS  read-only
    STATUS  mandatory
    DESCRIPTION
        "This variable displays the status of the entry.
        This entry value is only valid(1). And enable to response
        this entry when pf5000OspfIfType is nbma."
    ::= { pf5000OspfNbrEntry 10 }

pf5000OspfNbmaNbrPermanence OBJECT-TYPE
    SYNTAX  INTEGER {
        dynamic (1),        -- learned through protocol
        permanent (2)       -- configured address
    }
    ACCESS  read-only
    STATUS  mandatory
    DESCRIPTION
        "This variable displays the status of the entry."
    ::= { pf5000OspfNbrEntry 11 }

pf5000OspfVirtNbrTable OBJECT-TYPE
    SYNTAX  SEQUENCE OF Pf5000OspfVirtNbrEntry
    ACCESS  not-accessible
    STATUS  mandatory
    DESCRIPTION
        "A table of virtual neighbor information."
    ::= { pf5000Ospf 11 }

pf5000OspfVirtNbrEntry OBJECT-TYPE
    SYNTAX  Pf5000OspfVirtNbrEntry
    ACCESS  not-accessible
    STATUS  mandatory
    DESCRIPTION
        "Virtual neighbor information."
    INDEX { pf5000OspfVirtNbrDomainNumber,
            pf5000OspfVirtNbrArea,
            pf5000OspfVirtNbrRtrId }
    ::= { pf5000OspfVirtNbrTable 1 }

    Pf5000OspfVirtNbrEntry ::=
        SEQUENCE {
            pf5000OspfVirtNbrDomainNumber    INTEGER,
            pf5000OspfVirtNbrArea            IpAddress,
            pf5000OspfVirtNbrRtrId           IpAddress,
            pf5000OspfVirtNbrIpAddr          IpAddress,
            pf5000OspfVirtNbrOptions         INTEGER,
            pf5000OspfVirtNbrState           INTEGER,
            pf5000OspfVirtNbrEvents          Counter,
            pf5000OspfVirtNbrLsRetransQLen   Gauge
        }

pf5000OspfVirtNbrDomainNumber OBJECT-TYPE
    SYNTAX  INTEGER
    ACCESS  read-only
    STATUS  mandatory
    DESCRIPTION
        "The domain number."
    ::= { pf5000OspfVirtNbrEntry 1 }

pf5000OspfVirtNbrArea OBJECT-TYPE
    SYNTAX  IpAddress
    ACCESS  read-only
    STATUS  mandatory
    DESCRIPTION
        "The Transit Area Identifier."
    ::= { pf5000OspfVirtNbrEntry 2 }

pf5000OspfVirtNbrRtrId OBJECT-TYPE
    SYNTAX  IpAddress
    ACCESS  read-only
    STATUS  mandatory
    DESCRIPTION
        "A integer  uniquely  identifying  the neighboring
         router in the Autonomous System."
    ::= { pf5000OspfVirtNbrEntry 3 }

pf5000OspfVirtNbrIpAddr OBJECT-TYPE
    SYNTAX  IpAddress
    ACCESS  read-only
    STATUS  mandatory
    DESCRIPTION
        "The IP address this Virtual Neighbor is using."
    ::= { pf5000OspfVirtNbrEntry 4 }

pf5000OspfVirtNbrOptions OBJECT-TYPE
    SYNTAX  INTEGER
    ACCESS  read-only
    STATUS  mandatory
    DESCRIPTION
        "A Bit Mask corresponding to the neighbor's options
         field.

         Bit 1, if set, indicates that the  system  will operate
         on Type of Service metrics other than TOS 0. If zero,
         the neighbor will  ignore  all metrics except the TOS
         0 metric.

         Bit 2, if set, indicates  that  the  system  is Network
         Multicast  capable; ie, that it implements OSPF Multicast
         Routing."
    ::= { pf5000OspfVirtNbrEntry 5 }

pf5000OspfVirtNbrState OBJECT-TYPE
    SYNTAX  INTEGER {
        down (1),
        attempt (2),
        init (3),
        twoWay (4),
        exchangeStart (5),
        exchange (6),
        loading (7),
        full (8)
    }
    ACCESS  read-only
    STATUS  mandatory
    DESCRIPTION
        "The state of the  Virtual  Neighbor  Relationship."
    ::= { pf5000OspfVirtNbrEntry 6 }

pf5000OspfVirtNbrEvents OBJECT-TYPE
    SYNTAX  Counter
    ACCESS  read-only
    STATUS  mandatory
    DESCRIPTION
        "The number of times this virtual link has changed
        its state, or an error has occurred."
    ::= { pf5000OspfVirtNbrEntry 7 }

pf5000OspfVirtNbrLsRetransQLen OBJECT-TYPE
    SYNTAX  Gauge
    ACCESS  read-only
    STATUS  mandatory
    DESCRIPTION
        "The current length of the retransmission queue."
    ::= { pf5000OspfVirtNbrEntry 8 }

pf5000OspfExtLsdbTable OBJECT-TYPE
    SYNTAX  SEQUENCE OF Pf5000OspfExtLsdbEntry
    ACCESS  not-accessible
    STATUS  mandatory
    DESCRIPTION
        "The OSPF Process's Links State Database."
    ::= { pf5000Ospf 12 }

pf5000OspfExtLsdbEntry OBJECT-TYPE
    SYNTAX  Pf5000OspfExtLsdbEntry
    ACCESS  not-accessible
    STATUS  mandatory
    DESCRIPTION
        "A single Link State Advertisement."
    INDEX { pf5000OspfExtLsdbDomainNumber,
            pf5000OspfExtLsdbType,
            pf5000OspfExtLsdbLsid,
            pf5000OspfExtLsdbRouterId }
    ::= { pf5000OspfExtLsdbTable 1 }

    Pf5000OspfExtLsdbEntry ::=
        SEQUENCE {
            pf5000OspfExtLsdbDomainNumber    INTEGER,
            pf5000OspfExtLsdbType            INTEGER,
            pf5000OspfExtLsdbLsid            IpAddress,
            pf5000OspfExtLsdbRouterId        IpAddress,
            pf5000OspfExtLsdbSequence        INTEGER,
            pf5000OspfExtLsdbAge             INTEGER,
            pf5000OspfExtLsdbChecksum        INTEGER,
            pf5000OspfExtLsdbAdvertisement   OCTET STRING
        }

pf5000OspfExtLsdbDomainNumber OBJECT-TYPE
    SYNTAX  INTEGER
    ACCESS  read-only
    STATUS  mandatory
    DESCRIPTION
        "OSPF domain number."
    ::= { pf5000OspfExtLsdbEntry 1 }

pf5000OspfExtLsdbType OBJECT-TYPE
    SYNTAX  INTEGER {
        asExternalLink (5)
    }
    ACCESS  read-only
    STATUS  mandatory
    DESCRIPTION
        "The type  of  the  link  state  advertisement."
    ::= { pf5000OspfExtLsdbEntry 2 }

pf5000OspfExtLsdbLsid OBJECT-TYPE
    SYNTAX  IpAddress
    ACCESS  read-only
    STATUS  mandatory
    DESCRIPTION
        "The Link State ID is an LS Type Specific field
         containing either a Router ID or an IP Address;
         it identifies the piece of the  routing  domain
         that is being described by the advertisement."
    ::= { pf5000OspfExtLsdbEntry 3 }

pf5000OspfExtLsdbRouterId OBJECT-TYPE
    SYNTAX  IpAddress
    ACCESS  read-only
    STATUS  mandatory
    DESCRIPTION
        "The 32 bit number that uniquely identifies the
        originating router in the Autonomous System."
    ::= { pf5000OspfExtLsdbEntry 4 }

pf5000OspfExtLsdbSequence OBJECT-TYPE
    SYNTAX  INTEGER
    ACCESS  read-only
    STATUS  mandatory
    DESCRIPTION
        "The sequence number field is a  signed  32-bit integer."
    ::= { pf5000OspfExtLsdbEntry 5 }

pf5000OspfExtLsdbAge OBJECT-TYPE
    SYNTAX  INTEGER
    ACCESS  read-only
    STATUS  mandatory
    DESCRIPTION
        "The age of the link state advertisement in seconds."
    ::= { pf5000OspfExtLsdbEntry 6 }

pf5000OspfExtLsdbChecksum OBJECT-TYPE
    SYNTAX  INTEGER
    ACCESS  read-only
    STATUS  mandatory
    DESCRIPTION
        "This field is the  checksum  of  the  complete
         contents  of  the  advertisement, excepting the
         age field.  The age field is excepted  so  that
         an   advertisement's  age  can  be  incremented
         without updating the  checksum."
    ::= { pf5000OspfExtLsdbEntry 7 }

pf5000OspfExtLsdbAdvertisement OBJECT-TYPE
    SYNTAX  OCTET STRING
    ACCESS  read-only
    STATUS  mandatory
    DESCRIPTION
        "The entire Link State Advertisement, including its header."
    ::= { pf5000OspfExtLsdbEntry 8 }

pf5000OspfAreaAggregateTable OBJECT-TYPE
    SYNTAX  SEQUENCE OF Pf5000OspfAreaAggregateEntry
    ACCESS  not-accessible
    STATUS  mandatory
    DESCRIPTION
        "A range of IP addresses  specified  by  an  IP
        address/IP  network  mask  pair."
    ::= { pf5000Ospf 14 }

pf5000OspfAreaAggregateEntry OBJECT-TYPE
    SYNTAX  Pf5000OspfAreaAggregateEntry
    ACCESS  not-accessible
    STATUS  mandatory
    DESCRIPTION
        "A range of IP addresses  specified  by  an  IP
        address/IP  network  mask  pair."
    INDEX { pf5000OspfAreaAggregateDomainNumber,
            pf5000OspfAreaAggregateAreaID,
            pf5000OspfAreaAggregateLsdbType,
            pf5000OspfAreaAggregateNet,
            pf5000OspfAreaAggregateMask }
    ::= { pf5000OspfAreaAggregateTable 1 }

    Pf5000OspfAreaAggregateEntry ::=
        SEQUENCE {
            pf5000OspfAreaAggregateDomainNumber  INTEGER,
            pf5000OspfAreaAggregateAreaID        IpAddress,
            pf5000OspfAreaAggregateLsdbType      INTEGER,
            pf5000OspfAreaAggregateNet           IpAddress,
            pf5000OspfAreaAggregateMask          IpAddress,
            pf5000OspfAreaAggregateStatus        INTEGER,
            pf5000OspfAreaAggregateEffect        INTEGER
        }

pf5000OspfAreaAggregateDomainNumber OBJECT-TYPE
    SYNTAX  INTEGER
    ACCESS  read-only
    STATUS  mandatory
    DESCRIPTION
        "OSPF domain number."
    ::= { pf5000OspfAreaAggregateEntry 1 }

pf5000OspfAreaAggregateAreaID OBJECT-TYPE
    SYNTAX  IpAddress
    ACCESS  read-only
    STATUS  mandatory
    DESCRIPTION
        "The Area the Address Aggregate is to be found within."
    ::= { pf5000OspfAreaAggregateEntry 2 }

pf5000OspfAreaAggregateLsdbType OBJECT-TYPE
    SYNTAX  INTEGER {
        summaryLink (3),
        nssaExternalLink (7)
    }
    ACCESS  read-only
    STATUS  mandatory
    DESCRIPTION
        "The type of the Address Aggregate. This field
         specifies  the  Lsdb type that this Address 
         Aggregate applies to."
    ::= { pf5000OspfAreaAggregateEntry 3 }

pf5000OspfAreaAggregateNet OBJECT-TYPE
    SYNTAX  IpAddress
    ACCESS  read-only
    STATUS  mandatory
    DESCRIPTION
        "The IP Address of the Net or Subnet indicated by the range."
    ::= { pf5000OspfAreaAggregateEntry 4 }

pf5000OspfAreaAggregateMask OBJECT-TYPE
    SYNTAX  IpAddress
    ACCESS  read-only
    STATUS  mandatory
    DESCRIPTION
        "The Subnet Mask that pertains to the Net or Subnet."
    ::= { pf5000OspfAreaAggregateEntry 5 }

pf5000OspfAreaAggregateStatus OBJECT-TYPE
    SYNTAX  INTEGER {
        active(1)
    }
    ACCESS  read-only
    STATUS  mandatory
    DESCRIPTION
        "This variable displays the status of  the  entry.
        This entry value is only valid(1)."
    ::= { pf5000OspfAreaAggregateEntry 6 }

pf5000OspfAreaAggregateEffect OBJECT-TYPE
    SYNTAX  INTEGER {
        advertiseMatching (1),
        doNotAdvertiseMatching (2)
    }
    ACCESS  read-only
    STATUS  mandatory
    DESCRIPTION
        "Subnets subsumed by ranges either trigger  the
         advertisement  of  the indicated aggregate (ad-
         vertiseMatching), or result in the subnet's not
         being advertised at all outside the area."
    ::= { pf5000OspfAreaAggregateEntry 7 }

pf5000OspfTrapControlTable OBJECT-TYPE
    SYNTAX  SEQUENCE OF Pf5000OspfTrapControlEntry
    ACCESS  not-accessible
    STATUS  mandatory
    DESCRIPTION
        "The table about trap information."
    ::= { pf5000OspfTrap 1 }

pf5000OspfTrapControlEntry OBJECT-TYPE
    SYNTAX  Pf5000OspfTrapControlEntry
    ACCESS  not-accessible
    STATUS  mandatory
    DESCRIPTION
        "The Entry about trap information."
    INDEX { pf5000OspfTrapDomainNumber }
    ::= { pf5000OspfTrapControlTable 1 }

    Pf5000OspfTrapControlEntry ::=
    SEQUENCE {
        pf5000OspfTrapDomainNumber
            INTEGER,
        pf5000OspfSetTrap
            OCTET STRING,
        pf5000OspfConfigErrorType
            INTEGER,
        pf5000OspfPacketType
            INTEGER,
        pf5000OspfPacketSrc
            IpAddress
    }

pf5000OspfTrapDomainNumber OBJECT-TYPE
    SYNTAX  INTEGER
    ACCESS  read-only
    STATUS  mandatory
    DESCRIPTION
        "pf5000OspfTrap domain number."
    ::= { pf5000OspfTrapControlEntry 1 }

pf5000OspfSetTrap OBJECT-TYPE
    SYNTAX  OCTET STRING
    ACCESS  read-write
    STATUS  mandatory
    DESCRIPTION
        "A four-octet string serving as a bit  map  for
        the trap events defined by the OSPF traps. This
        object is used to enable and  disable  specific
        OSPF   traps   where  a  1  in  the  bit  field
        represents enabled.  The right-most bit  (least
        significant) represents trap 0."
    ::= { pf5000OspfTrapControlEntry 2 }

pf5000OspfConfigErrorType OBJECT-TYPE
    SYNTAX  INTEGER {
        badVersion (1),
        areaMismatch (2),
        unknownNbmaNbr (3), -- Router is Dr eligible
        unknownVirtualNbr (4),
        authTypeMismatch(5),
        authFailure (6),
        netMaskMismatch (7),
        helloIntervalMismatch (8),
        deadIntervalMismatch (9),
        optionMismatch (10),
        duplicateRouterId (12),
        noError (13)
    }
    ACCESS   read-only
    STATUS   mandatory
    DESCRIPTION
        "Potential types  of  configuration  conflicts.
        Used  by the ospfConfigError and ospfConfigVir-
        tError traps."
    ::= { pf5000OspfTrapControlEntry 3 }

pf5000OspfPacketType OBJECT-TYPE
    SYNTAX  INTEGER {
        hello (1),
        dbDescript (2),
        lsReq (3),
        lsUpdate (4),
        lsAck (5), 
        nullPacket (6)
    }
    ACCESS   read-only
    STATUS   mandatory
    DESCRIPTION
        "OSPF packet types."
    ::= { pf5000OspfTrapControlEntry 4 }

pf5000OspfPacketSrc OBJECT-TYPE
    SYNTAX   IpAddress
    ACCESS   read-only
    STATUS   mandatory
    DESCRIPTION
        "The IP address of an inbound packet that  can-
        not be identified by a neighbor instance."
    ::= { pf5000OspfTrapControlEntry 5 }

-- pf5000Ospfv3

pf5000Ospfv3GeneralTable OBJECT-TYPE
    SYNTAX  SEQUENCE OF Pf5000Ospfv3GeneralEntry
    ACCESS  not-accessible
    STATUS  mandatory
    DESCRIPTION
        "The table which ospfv3 information is stored in."
    ::= { pf5000Ospfv3 1 }

pf5000Ospfv3GeneralEntry OBJECT-TYPE
    SYNTAX  Pf5000Ospfv3GeneralEntry
    ACCESS  not-accessible
    STATUS  mandatory
    DESCRIPTION
        "The list of the ospfv3 information."
    INDEX { pf5000Ospfv3GeneralDomainNumber }
    ::= { pf5000Ospfv3GeneralTable 1 }

    Pf5000Ospfv3GeneralEntry ::=
    SEQUENCE {
        pf5000Ospfv3GeneralDomainNumber
            INTEGER,
        pf5000Ospfv3RouterId
            IpAddress,
        pf5000Ospfv3AdminStat
            INTEGER,
        pf5000Ospfv3VersionNumber
            INTEGER,
        pf5000Ospfv3AreaBdrRtrStatus
            INTEGER,
        pf5000Ospfv3ASBdrRtrStatus
            INTEGER,
        pf5000Ospfv3AsScopeLsaCount
            Gauge,
        pf5000Ospfv3AsScopeLsaCksumSum
            INTEGER,
        pf5000Ospfv3OriginateNewLsas
            Counter,
        pf5000Ospfv3RxNewLsas
            Counter,
        pf5000Ospfv3ExtAreaLsdbLimit
            INTEGER,
        pf5000Ospfv3MulticastExtensions
            INTEGER,
        pf5000Ospfv3DemandExtensions
            INTEGER,
        pf5000Ospfv3TrafficEngineeringSupport
            INTEGER
    }

pf5000Ospfv3GeneralDomainNumber OBJECT-TYPE
    SYNTAX  INTEGER
    ACCESS  read-only
    STATUS  mandatory
    DESCRIPTION
        "ospfv3 domain number."
    ::= { pf5000Ospfv3GeneralEntry 1 }

pf5000Ospfv3RouterId OBJECT-TYPE
    SYNTAX  IpAddress
    ACCESS  read-only
    STATUS  mandatory
    DESCRIPTION
        "A  32-bit  integer  uniquely  identifying  the
        router in the Autonomous System.
        By convention, to  ensure  uniqueness, this
        should  default  to  the  value  of  one of the
        router's IPv4 interface addresses if IPv4 is
        configured."
    ::= { pf5000Ospfv3GeneralEntry 2 }

pf5000Ospfv3AdminStat OBJECT-TYPE
    SYNTAX  INTEGER
    ACCESS  read-only
    STATUS  mandatory
    DESCRIPTION
        "The  administrative  status  of  pf5000Ospfv3  in  the
        router.  The  value 'enabled' denotes that the
        pf5000Ospfv3 Process is active on at least  one  inter-
        face;  'disabled'  disables  it  on  all inter-
        faces."
    ::= { pf5000Ospfv3GeneralEntry 3 }

pf5000Ospfv3VersionNumber OBJECT-TYPE
    SYNTAX  INTEGER { version3 (3) }
    ACCESS  read-only
    STATUS  mandatory
    DESCRIPTION
        "The version number of OSPF for IPv6 is 3."
    ::= { pf5000Ospfv3GeneralEntry 4 }

pf5000Ospfv3AreaBdrRtrStatus OBJECT-TYPE
    SYNTAX  INTEGER
    ACCESS  read-only
    STATUS  mandatory
    DESCRIPTION
        "A flag to note whether this router is an  area
        border router."
    REFERENCE
        "OSPF Version 2, Section 3 Splitting the AS into
        Areas"
    ::= { pf5000Ospfv3GeneralEntry 5 }

pf5000Ospfv3ASBdrRtrStatus OBJECT-TYPE
    SYNTAX  INTEGER
    ACCESS  read-only
    STATUS  mandatory
    DESCRIPTION
        "A flag to note whether this router is  config-
        ured as an Autonomous System border router."
    REFERENCE
        "OSPF Version 2, Section 3.3  Classification  of
        routers"
    ::= { pf5000Ospfv3GeneralEntry 6 }

pf5000Ospfv3AsScopeLsaCount OBJECT-TYPE
    SYNTAX  Gauge
    ACCESS  read-only
    STATUS  mandatory
    DESCRIPTION
        "The number of AS-Scope (e.g. AS-External) link-state
        advertisements in the link-state database."
    ::= { pf5000Ospfv3GeneralEntry 7 }

pf5000Ospfv3AsScopeLsaCksumSum OBJECT-TYPE
    SYNTAX  INTEGER
    ACCESS  read-only
    STATUS  mandatory
    DESCRIPTION
        "The 32-bit unsigned sum of the LS checksums of
        the  AS-scoped link-state advertisements  con-
        tained in the link-state database. This sum
        can  be  used  to determine if there has been a
        change in a router's link state  database,  and
        to  compare  the  link-state  database  of  two
        routers."
    ::= { pf5000Ospfv3GeneralEntry 8 }

pf5000Ospfv3OriginateNewLsas OBJECT-TYPE
    SYNTAX  Counter
    ACCESS  read-only
    STATUS  mandatory
    DESCRIPTION
        "The number of  new  link-state  advertisements
        that  have been originated.  This number is in-
        cremented each time the router originates a new
        LSA."
    ::= { pf5000Ospfv3GeneralEntry 9 }

pf5000Ospfv3RxNewLsas OBJECT-TYPE
    SYNTAX  Counter
    ACCESS  read-only
    STATUS  mandatory
    DESCRIPTION
        "The number of  link-state  advertisements  re-
        ceived  determined  to  be  new instantiations.
        This number does not include  newer  instantia-
        tions  of self-originated link-state advertise-
        ments."
    ::= { pf5000Ospfv3GeneralEntry 10 }

pf5000Ospfv3ExtAreaLsdbLimit OBJECT-TYPE
    SYNTAX  INTEGER (-1..'7FFFFFFF'h)
    ACCESS  read-only
    STATUS  mandatory
    DESCRIPTION
        "The  maximum   number   of   non-default   AS-
        external-LSAs entries that can be stored in the
        link-state database.  If the value is -1,  then
        there is no limit.
        When the number of non-default AS-external-LSAs
        in  a  router's  link-state  database  reaches
        pf5000Ospfv3ExtAreaLsdbLimit, the router  enters  Overflow-
        State.  The   router  never  holds  more  than
        pf5000Ospfv3ExtAreaLsdbLimit  non-default  AS-external-LSAs
        in  its  database. OspfExtAreaLsdbLimit MUST be set
        identically in all routers attached to the pf5000Ospfv3
        backbone  and/or  any regular pf5000Ospfv3 area. (i.e.,
        pf5000Ospfv3 stub areas and NSSAs are excluded)."
    DEFVAL { -1 }
    ::= { pf5000Ospfv3GeneralEntry 11 }

pf5000Ospfv3MulticastExtensions OBJECT-TYPE
    SYNTAX  INTEGER
    ACCESS  read-only
    STATUS  mandatory
    DESCRIPTION
        "A Bit Mask indicating whether  the  router  is
        forwarding  IPv6  multicast datagrams
        based on the algorithms defined in  the  Multi-
        cast Extensions to OSPF.
        Bit 0, if set, indicates that  the  router  can
        forward  IPv6 multicast datagrams in the router's
        directly attached areas (called intra-area mul-
        ticast routing).
        Bit 1, if set, indicates that  the  router  can
        forward  IPv6  multicast  datagrams  between pf5000Ospfv3
        areas (called inter-area multicast routing).
        Bit 2, if set, indicates that  the  router  can
        forward  IPv6  multicast  datagrams between Auto-
        nomous Systems (called inter-AS multicast rout-
        ing).
        Only certain combinations of bit  settings are
        allowed,  namely: 0 (no multicast forwarding is
        enabled), 1 (intra-area multicasting  only),  3
        (intra-area  and  inter-area  multicasting),  5
        (intra-area and inter-AS  multicasting)  and  7
        (multicasting  everywhere). By default, no mul-
        ticast forwarding is enabled."
    DEFVAL { 0 }
    ::= { pf5000Ospfv3GeneralEntry 12 }

pf5000Ospfv3DemandExtensions OBJECT-TYPE
    SYNTAX  INTEGER
    ACCESS  read-only
    STATUS  mandatory
    DESCRIPTION
        "The router's support for demand routing."
    REFERENCE
        "OSPF Version 2, Appendix on Demand Routing"
    ::= { pf5000Ospfv3GeneralEntry 14 }

pf5000Ospfv3TrafficEngineeringSupport OBJECT-TYPE
    SYNTAX  INTEGER
    ACCESS  read-only
    STATUS  mandatory
    DESCRIPTION
        "The router's support for traffic engineering
        extensions."
    ::= { pf5000Ospfv3GeneralEntry 15 }

--  The pf5000Ospfv3 Area Data Structure contains information
--  regarding the various areas. The interfaces and
--  virtual links are configured as part of these areas.
--  Area 0.0.0.0, by definition, is the Backbone Area

pf5000Ospfv3AreaTable OBJECT-TYPE
    SYNTAX  SEQUENCE OF Pf5000Ospfv3AreaEntry
    ACCESS  not-accessible
    STATUS  mandatory
    DESCRIPTION
        "Information describing the configured  parame-
        ters  and cumulative statistics of the router's
        attached areas."
    REFERENCE
        "OSPF Version 2, Section 6  The Area Data Struc-
        ture"
    ::= { pf5000Ospfv3 2 }

pf5000Ospfv3AreaEntry OBJECT-TYPE
    SYNTAX  Pf5000Ospfv3AreaEntry
    ACCESS  not-accessible
    STATUS  mandatory
    DESCRIPTION
        "Information describing the configured  parame-
        ters  and  cumulative  statistics of one of the
        router's attached areas."
        INDEX { pf5000Ospfv3AreaDomainNumber,
                pf5000Ospfv3AreaId }
    ::= { pf5000Ospfv3AreaTable 1 }

    Pf5000Ospfv3AreaEntry ::=
        SEQUENCE {
            pf5000Ospfv3AreaDomainNumber
                INTEGER,
            pf5000Ospfv3AreaId
                IpAddress,
            pf5000Ospfv3ImportAsExtern
                INTEGER,
            pf5000Ospfv3SpfRuns
                Counter,
            pf5000Ospfv3AreaBdrRtrCount
                Gauge,
            pf5000Ospfv3AsBdrRtrCount
                Gauge,
            pf5000Ospfv3AreaScopeLsaCount
                Gauge,
            pf5000Ospfv3AreaScopeLsaCksumSum
                INTEGER,
            pf5000Ospfv3AreaSummary
                INTEGER,
            pf5000Ospfv3AreaStatus
                INTEGER,
            pf5000Ospfv3StubMetric
                INTEGER
        }

pf5000Ospfv3AreaDomainNumber OBJECT-TYPE
    SYNTAX  INTEGER
    ACCESS  read-only
    STATUS  mandatory
    DESCRIPTION
        "ospfv3 domain number."
    ::= { pf5000Ospfv3AreaEntry 1 }

pf5000Ospfv3AreaId OBJECT-TYPE
    SYNTAX  IpAddress
    ACCESS  read-only
    STATUS  mandatory
    DESCRIPTION
        "A 32-bit integer uniquely identifying an area.
        Area ID 0.0.0.0 is used for the pf5000Ospfv3 backbone."
    REFERENCE
        "OSPF Version 2, Appendix C.2 Area parameters"
    ::= { pf5000Ospfv3AreaEntry 2 }

pf5000Ospfv3ImportAsExtern OBJECT-TYPE
    SYNTAX  INTEGER {
        importExternal (1),   -- normal area
        importNoExternal (2), -- stub area
        importNssa (3)        -- not-so-stubby-area
    }
    ACCESS  read-only
    STATUS  mandatory
    DESCRIPTION
        "Indicates whether an area is a Stub area, NSSA, or
        standard area. AS-scope LSAs are not imported into Stub
        Areas or NSSAs. NSSAs import AS-External data as Type-7
        LSAs which have Area-scope"
    REFERENCE
        "OSPF Version 2, Appendix C.2 Area parameters"
        DEFVAL { importExternal }
    ::= { pf5000Ospfv3AreaEntry 3 }

pf5000Ospfv3SpfRuns OBJECT-TYPE
    SYNTAX  Counter
    ACCESS  read-only
    STATUS  mandatory
    DESCRIPTION
        "The number of times that the intra-area  route
        table  has  been  calculated  using this area's
        link-state database.  This  is  typically  done
        using Dijkstra's algorithm."
    ::= { pf5000Ospfv3AreaEntry 4 }

pf5000Ospfv3AreaBdrRtrCount OBJECT-TYPE
    SYNTAX  Gauge
    ACCESS  read-only
    STATUS  mandatory
    DESCRIPTION
        "The total number of area border routers reach-
        able within this area. This is initially zero,
        and is calculated in each SPF Pass."
    ::= { pf5000Ospfv3AreaEntry 5 }

pf5000Ospfv3AsBdrRtrCount OBJECT-TYPE
    SYNTAX  Gauge
    ACCESS  read-only
    STATUS  mandatory
    DESCRIPTION
        "The total number of Autonomous  System  border
        routers  reachable  within  this area.  This is
        initially zero, and is calculated in  each  SPF
        Pass."
    ::= { pf5000Ospfv3AreaEntry 6 }

pf5000Ospfv3AreaScopeLsaCount OBJECT-TYPE
    SYNTAX  Gauge
    ACCESS  read-only
    STATUS  mandatory
    DESCRIPTION
    "The total number of Area-Scope link-state
    advertisements in  this  area's link-state
    database."
    ::= { pf5000Ospfv3AreaEntry 7 }

pf5000Ospfv3AreaScopeLsaCksumSum OBJECT-TYPE
    SYNTAX  INTEGER
    ACCESS  read-only
    STATUS  mandatory
    DESCRIPTION
        "The 32-bit unsigned sum of the Area-Scope link-state
        advertisements'  LS  checksums  contained in this
        area's link-state database.  The sum can be used
        to determine if  there  has been  a  change  in a
        router's link state database, and to compare the
        link-state database of two routers."
        DEFVAL  { 0 }
    ::= { pf5000Ospfv3AreaEntry 8 }

pf5000Ospfv3AreaSummary OBJECT-TYPE
    SYNTAX  INTEGER {
        noAreaSummary (1),
        sendAreaSummary (2)
    }
    ACCESS  read-only
    STATUS  mandatory
    DESCRIPTION
        "The variable pf5000Ospfv3AreaSummary controls the  im-
        port  of  summary LSAs into stub areas.  It has
        no effect on other areas.
        If it is noAreaSummary, the router will neither
        originate  nor  propagate summary LSAs into the
        stub area.  It will rely entirely  on  its  de-
        fault route.
        If it is sendAreaSummary, the router will  both
        summarize and propagate summary LSAs."
        DEFVAL  { noAreaSummary }
    ::= { pf5000Ospfv3AreaEntry 9 }

pf5000Ospfv3AreaStatus OBJECT-TYPE
    SYNTAX  INTEGER
    ACCESS  read-only
    STATUS  mandatory
    DESCRIPTION
        "This variable displays the status of  the  en-
        try.  Setting it to 'invalid' has the effect of
        rendering it inoperative.  The internal  effect
        (row removal) is implementation dependent."
    ::= { pf5000Ospfv3AreaEntry 10 }

pf5000Ospfv3StubMetric OBJECT-TYPE
    SYNTAX  INTEGER
--    ACCESS  read-create
    ACCESS  read-only
    STATUS  mandatory
    DESCRIPTION
        "The metric value advertised for the default route
        into Stub and NSSA areas."
    ::= { pf5000Ospfv3AreaEntry 11 }

--    pf5000Ospfv3 AS-Scope Link State Database
--        The Link State Database contains the AS-Scope Link State
--        Advertisements from throughout the areas that the
--        device is attached to.

pf5000Ospfv3AsLsdbTable OBJECT-TYPE
    SYNTAX  SEQUENCE OF Pf5000Ospfv3AsLsdbEntry
    ACCESS  not-accessible
    STATUS  mandatory
    DESCRIPTION
        "The pf5000Ospfv3 Process's AS-Scope Link State Database."
    ::= { pf5000Ospfv3 3 }

pf5000Ospfv3AsLsdbEntry OBJECT-TYPE
    SYNTAX  Pf5000Ospfv3AsLsdbEntry
    ACCESS  not-accessible
    STATUS  mandatory
    DESCRIPTION
    "A single AS-Scope Link State Advertisement."
    INDEX { pf5000Ospfv3AsLsdbDomainNumber,
            pf5000Ospfv3AsLsdbType,
            pf5000Ospfv3AsLsdbRouterId,
            pf5000Ospfv3AsLsdbLsid }
    ::= { pf5000Ospfv3AsLsdbTable 1 }

    Pf5000Ospfv3AsLsdbEntry ::=
        SEQUENCE {
            pf5000Ospfv3AsLsdbDomainNumber
                INTEGER,
            pf5000Ospfv3AsLsdbType
                INTEGER,
            pf5000Ospfv3AsLsdbRouterId
                IpAddress,
            pf5000Ospfv3AsLsdbLsid
                IpAddress,
            pf5000Ospfv3AsLsdbSequence
                INTEGER,
            pf5000Ospfv3AsLsdbAge
                INTEGER,
            pf5000Ospfv3AsLsdbChecksum
                INTEGER,
            pf5000Ospfv3AsLsdbAdvertisement
                OCTET STRING
        }

pf5000Ospfv3AsLsdbDomainNumber OBJECT-TYPE
    SYNTAX  INTEGER
    ACCESS  read-only
    STATUS  mandatory
    DESCRIPTION
        "ospfv3 domain number."
    ::= { pf5000Ospfv3AsLsdbEntry 1 }

pf5000Ospfv3AsLsdbType OBJECT-TYPE
    SYNTAX  INTEGER {
        asExternalLink (16389)  -- 0x4005
    }
    ACCESS  read-only
    STATUS  mandatory
    DESCRIPTION
        "The type  of  the  link  state  advertisement.
        Each  link state type has a separate advertise-
        ment format. Unrecognized AS-Scope LSAs with the
        U-bit set are also store in this database."
    ::= { pf5000Ospfv3AsLsdbEntry 2 }

pf5000Ospfv3AsLsdbRouterId OBJECT-TYPE
    SYNTAX  IpAddress
    ACCESS  read-only
    STATUS  mandatory
    DESCRIPTION
        "The 32 bit number that uniquely identifies the
        originating router in the Autonomous System."
    REFERENCE
        "OSPF Version 2, Appendix C.1 Global parameters"
    ::= { pf5000Ospfv3AsLsdbEntry 3 }

pf5000Ospfv3AsLsdbLsid OBJECT-TYPE
    SYNTAX  IpAddress
    ACCESS  read-only
    STATUS  mandatory
    DESCRIPTION
    "The Link State ID is an LS Type Specific field
    containing either a Router ID or a unique identifier;
    it identifies the piece of the  routing  domain
    that is being described by the advertisement.
    In contrast to OSPF for IPv4, the LSID has no
    addressing semantics."
    ::= { pf5000Ospfv3AsLsdbEntry 4 }

--  Note that the OSPF Sequence Number is a 32 bit signed
--  integer.  It starts with the value '80000001'h,
--  or -'7FFFFFFF'h, and increments until '7FFFFFFF'h
--  Thus, a typical sequence number will be very negative.

pf5000Ospfv3AsLsdbSequence OBJECT-TYPE
    SYNTAX  INTEGER
    ACCESS  read-only
    STATUS  mandatory
    DESCRIPTION
        "The sequence number field is a  signed  32-bit
        integer.   It  is used to detect old and dupli-
        cate link state advertisements.  The  space  of
        sequence  numbers  is  linearly  ordered.  The
        larger the sequence number the more recent  the
        advertisement."
    REFERENCE
        "OSPF Version  2,  Section  12.1.6  LS  sequence
        number"
    ::= { pf5000Ospfv3AsLsdbEntry 5 }

pf5000Ospfv3AsLsdbAge OBJECT-TYPE
    SYNTAX  INTEGER  -- Should be 0..MaxAge
    ACCESS  read-only
    STATUS  mandatory
    DESCRIPTION
        "This field is the age of the link state adver-
        tisement in seconds."
    REFERENCE
        "OSPF Version 2, Section 12.1.1 LS age"
    ::= { pf5000Ospfv3AsLsdbEntry 6 }

pf5000Ospfv3AsLsdbChecksum OBJECT-TYPE
    SYNTAX  INTEGER
    ACCESS  read-only
    STATUS  mandatory
    DESCRIPTION
        "This field is the  checksum  of  the  complete
        contents  of  the  advertisement, excepting the
        age field.  The age field is excepted  so  that
        an  advertisement's  age  can  be  incremented
        without updating the  checksum.  The  checksum
        used  is  the same that is used for ISO connec-
        tionless datagrams; it is commonly referred  to
        as the Fletcher checksum."
    REFERENCE
        "OSPF Version 2, Section 12.1.7 LS checksum"
    ::= { pf5000Ospfv3AsLsdbEntry 7 }

pf5000Ospfv3AsLsdbAdvertisement OBJECT-TYPE
    SYNTAX  OCTET STRING (SIZE (1..65535))
    ACCESS  read-only
    STATUS  mandatory
    DESCRIPTION
    "The entire Link State Advertisement, including
    its header."
    ::= { pf5000Ospfv3AsLsdbEntry 8 }

--  pf5000Ospfv3 Area-Scope Link State Database
--  The Link State Database contains the Area-Scope Link State
--  Advertisements from throughout the area that the
--  device is attached to.

pf5000Ospfv3AreaLsdbTable OBJECT-TYPE
    SYNTAX  SEQUENCE OF Pf5000Ospfv3AreaLsdbEntry
    ACCESS  not-accessible
    STATUS  mandatory
    DESCRIPTION
        "The pf5000Ospfv3 Process's Area-Scope Link State Database."
    ::= { pf5000Ospfv3 4 }

pf5000Ospfv3AreaLsdbEntry OBJECT-TYPE
    SYNTAX  Pf5000Ospfv3AreaLsdbEntry
    ACCESS  not-accessible
    STATUS  mandatory
    DESCRIPTION
        "A single Area-Scope Link State Advertisement."
    INDEX { pf5000Ospfv3AreaLsdbDomainNumber,
            pf5000Ospfv3AreaLsdbAreaId,
            pf5000Ospfv3AreaLsdbType,
            pf5000Ospfv3AreaLsdbRouterId,
            pf5000Ospfv3AreaLsdbLsid }
    ::= { pf5000Ospfv3AreaLsdbTable 1 }

    Pf5000Ospfv3AreaLsdbEntry ::=
        SEQUENCE {
        pf5000Ospfv3AreaLsdbDomainNumber
            INTEGER,
        pf5000Ospfv3AreaLsdbAreaId
            IpAddress,
        pf5000Ospfv3AreaLsdbType
            INTEGER,
        pf5000Ospfv3AreaLsdbRouterId
            IpAddress,
        pf5000Ospfv3AreaLsdbLsid
            IpAddress,
        pf5000Ospfv3AreaLsdbSequence
            INTEGER,
        pf5000Ospfv3AreaLsdbAge
            INTEGER,
        pf5000Ospfv3AreaLsdbChecksum
            INTEGER,
        pf5000Ospfv3AreaLsdbAdvertisement
            OCTET STRING
    }

pf5000Ospfv3AreaLsdbDomainNumber OBJECT-TYPE
    SYNTAX  INTEGER
    ACCESS  read-only
    STATUS  mandatory
    DESCRIPTION
        "ospfv3 domain number."
    ::= { pf5000Ospfv3AreaLsdbEntry 1 }

pf5000Ospfv3AreaLsdbAreaId OBJECT-TYPE
    SYNTAX  IpAddress
    ACCESS  read-only
    STATUS  mandatory
    DESCRIPTION
        "The 32 bit identifier of the Area from which the
        LSA was received."
    REFERENCE
        "OSPF Version 2, Appendix C.2 Area parameters."
    ::= { pf5000Ospfv3AreaLsdbEntry 2 }

pf5000Ospfv3AreaLsdbType OBJECT-TYPE
    SYNTAX  INTEGER {
        routerLsa          (8193),  -- 0x2001
        networkLsa         (8194),  -- 0x2002
        interAreaPrefixLsa (8195),  -- 0x2003
        interAreaRouterLsa (8196),  -- 0x2004
        groupMembershipLsa (8198),  -- 0x2006
        nssaExternalLsa    (8199),  -- 0x2007
        intraAreaPrefixLsa (8201)   -- 0x2009
    }
    ACCESS  read-only
    STATUS  mandatory
    DESCRIPTION
        "The type  of  the  link  state  advertisement.
        Each  link state type has a separate advertise-
        ment format. Unrecognized Area-Scope LSAs with
        the U-bit set are also stored in this database."
    ::= { pf5000Ospfv3AreaLsdbEntry 3 }

pf5000Ospfv3AreaLsdbRouterId OBJECT-TYPE
    SYNTAX  IpAddress
    ACCESS  read-only
    STATUS  mandatory
    DESCRIPTION
        "The 32 bit number that uniquely identifies the
        originating router in the Autonomous System."
    REFERENCE
        "OSPF Version 2, Appendix C.1 Global parameters"
    ::= { pf5000Ospfv3AreaLsdbEntry 4 }

pf5000Ospfv3AreaLsdbLsid OBJECT-TYPE
    SYNTAX  IpAddress
    ACCESS  read-only
    STATUS  mandatory
    DESCRIPTION
        "The Link State ID is an LS Type Specific field
        containing either a Router ID or a unique identifier;
        it identifies the piece of the  routing  domain
        that is being described by the advertisement.
        In contrast to OSPF for IPv4, the LSID has no
        addressing semantics."
    ::= { pf5000Ospfv3AreaLsdbEntry 5 }

--  Note that the OSPF Sequence Number is a 32 bit signed
--  integer.  It starts with the value '80000001'h,
--  or -'7FFFFFFF'h, and increments until '7FFFFFFF'h
--  Thus, a typical sequence number will be very negative.

pf5000Ospfv3AreaLsdbSequence OBJECT-TYPE
    SYNTAX  INTEGER
    ACCESS  read-only
    STATUS  mandatory
    DESCRIPTION
        "The sequence number field is a  signed  32-bit
        integer.   It  is used to detect old and dupli-
        cate link state advertisements.  The  space  of
        sequence  numbers  is  linearly  ordered.   The
        larger the sequence number the more recent  the
        advertisement."
    REFERENCE
        "OSPF Version  2,  Section  12.1.6  LS  sequence
        number"
    ::= { pf5000Ospfv3AreaLsdbEntry 6 }

pf5000Ospfv3AreaLsdbAge OBJECT-TYPE
    SYNTAX  INTEGER  -- Should be 0..MaxAge
    ACCESS  read-only
    STATUS  mandatory
    DESCRIPTION
        "This field is the age of the link state adver-
        tisement in seconds."
    REFERENCE
        "OSPF Version 2, Section 12.1.1 LS age"
    ::= { pf5000Ospfv3AreaLsdbEntry 7 }

pf5000Ospfv3AreaLsdbChecksum OBJECT-TYPE
    SYNTAX  INTEGER
    ACCESS  read-only
    STATUS  mandatory
    DESCRIPTION
        "This field is the  checksum  of  the  complete
        contents  of  the  advertisement, excepting the
        age field.  The age field is excepted  so  that
        an  advertisement's  age  can  be  incremented
        without updating the  checksum.  The  checksum
        used  is  the same that is used for ISO connec-
        tionless datagrams; it is commonly referred  to
        as the Fletcher checksum."
    REFERENCE
        "OSPF Version 2, Section 12.1.7 LS checksum"
    ::= { pf5000Ospfv3AreaLsdbEntry 8 }

pf5000Ospfv3AreaLsdbAdvertisement OBJECT-TYPE
    SYNTAX  OCTET STRING (SIZE (1..65535))
    ACCESS  read-only
    STATUS  mandatory
    DESCRIPTION
        "The entire Link State Advertisement, including
        its header."
    ::= { pf5000Ospfv3AreaLsdbEntry 9 }

--  pf5000Ospfv3 Link-Scope Link State Database
--    The Link State Database contains the Link-Scope Link State
--    Advertisements from the links that the
--    device is attached to.

pf5000Ospfv3LinkLsdbTable OBJECT-TYPE
    SYNTAX  SEQUENCE OF Pf5000Ospfv3LinkLsdbEntry
    ACCESS  not-accessible
    STATUS  mandatory
    DESCRIPTION
        "The pf5000Ospfv3 Process's Link-Scope Link State Database."
    ::= { pf5000Ospfv3 5 }

pf5000Ospfv3LinkLsdbEntry OBJECT-TYPE
    SYNTAX  Pf5000Ospfv3LinkLsdbEntry
    ACCESS  not-accessible
    STATUS  mandatory
    DESCRIPTION
        "A single Link-Scope Link State Advertisement."
    INDEX { pf5000Ospfv3LinkLsdbDomainNumber,
            pf5000Ospfv3LinkLsdbIfIndex,
            pf5000Ospfv3LinkLsdbType,
            pf5000Ospfv3LinkLsdbRouterId,
            pf5000Ospfv3LinkLsdbLsid }
    ::= { pf5000Ospfv3LinkLsdbTable 1 }

    Pf5000Ospfv3LinkLsdbEntry ::=
        SEQUENCE {
            pf5000Ospfv3LinkLsdbDomainNumber
                INTEGER,
            pf5000Ospfv3LinkLsdbIfIndex
                INTEGER,
            pf5000Ospfv3LinkLsdbType
                INTEGER,
            pf5000Ospfv3LinkLsdbRouterId
                IpAddress,
            pf5000Ospfv3LinkLsdbLsid
                IpAddress,
            pf5000Ospfv3LinkLsdbSequence
                INTEGER,
            pf5000Ospfv3LinkLsdbAge
                INTEGER,
            pf5000Ospfv3LinkLsdbChecksum
                INTEGER,
            pf5000Ospfv3LinkLsdbAdvertisement
                OCTET STRING
        }

pf5000Ospfv3LinkLsdbDomainNumber OBJECT-TYPE
    SYNTAX  INTEGER
    ACCESS  read-only
    STATUS  mandatory
    DESCRIPTION
        "ospfv3 domain number."
    ::= { pf5000Ospfv3LinkLsdbEntry 1 }

pf5000Ospfv3LinkLsdbIfIndex OBJECT-TYPE
    SYNTAX  INTEGER
    ACCESS  read-only
    STATUS  mandatory
    DESCRIPTION
        "The identifier of the link from which the LSA
        was received."
    REFERENCE
        "OSPF Version 2, Appendix C.2 Area parameters"
    ::= { pf5000Ospfv3LinkLsdbEntry 2 }

pf5000Ospfv3LinkLsdbType OBJECT-TYPE
    SYNTAX  INTEGER {
        linkLsa (8)  -- 0x0008
    }
    ACCESS  read-only
    STATUS  mandatory
    DESCRIPTION
        "The type  of  the  link  state  advertisement.
        Each  link state type has a separate advertise-
        ment format. Unrecognized Link-Scope LSAs with
        the U-bit set are also stored in this database."
    ::= { pf5000Ospfv3LinkLsdbEntry 3 }

pf5000Ospfv3LinkLsdbRouterId OBJECT-TYPE
    SYNTAX  IpAddress
    ACCESS  read-only
    STATUS  mandatory
    DESCRIPTION
        "The 32 bit number that uniquely identifies the
        originating router in the Autonomous System."
    REFERENCE
        "OSPF Version 2, Appendix C.1 Global parameters"
    ::= { pf5000Ospfv3LinkLsdbEntry 4 }

pf5000Ospfv3LinkLsdbLsid OBJECT-TYPE
    SYNTAX  IpAddress
    ACCESS  read-only
    STATUS  mandatory
    DESCRIPTION
        "The Link State ID is an LS Type Specific field
        containing either a Router ID or a unique identifier;
        it identifies the piece of the  routing  domain
        that is being described by the advertisement.
        In contrast to OSPF for IPv4, the LSID has no
        addressing semantics."
    ::= { pf5000Ospfv3LinkLsdbEntry 5 }

--  Note that the OSPF Sequence Number is a 32 bit signed
--  integer.  It starts with the value '80000001'h,
--  or -'7FFFFFFF'h, and increments until '7FFFFFFF'h
--  Thus, a typical sequence number will be very negative.

pf5000Ospfv3LinkLsdbSequence OBJECT-TYPE
    SYNTAX  INTEGER
    ACCESS  read-only
    STATUS  mandatory
    DESCRIPTION
        "The sequence number field is a  signed  32-bit
        integer.   It  is used to detect old and dupli-
        cate link state advertisements.  The  space  of
        sequence  numbers  is  linearly  ordered.  The
        larger the sequence number the more recent  the
        advertisement."
    REFERENCE
        "OSPF Version  2,  Section  12.1.6  LS  sequence
        number"
    ::= { pf5000Ospfv3LinkLsdbEntry 6 }

pf5000Ospfv3LinkLsdbAge OBJECT-TYPE
    SYNTAX  INTEGER  -- Should be 0..MaxAge
    ACCESS  read-only
    STATUS   mandatory
    DESCRIPTION
        "This field is the age of the link state adver-
        tisement in seconds."
    REFERENCE
        "OSPF Version 2, Section 12.1.1 LS age"
    ::= { pf5000Ospfv3LinkLsdbEntry 7 }

pf5000Ospfv3LinkLsdbChecksum OBJECT-TYPE
    SYNTAX  INTEGER
    ACCESS  read-only
    STATUS  mandatory
    DESCRIPTION
        "This field is the  checksum  of  the  complete
        contents  of  the  advertisement, excepting the
        age field.  The age field is excepted  so  that
        an  advertisement's  age  can  be  incremented
        without updating the  checksum.  The  checksum
        used  is  the same that is used for ISO connec-
        tionless datagrams; it is commonly referred  to
        as the Fletcher checksum."
    REFERENCE
        "OSPF Version 2, Section 12.1.7 LS checksum"
    ::= { pf5000Ospfv3LinkLsdbEntry 8 }

pf5000Ospfv3LinkLsdbAdvertisement OBJECT-TYPE
    SYNTAX  OCTET STRING (SIZE (1..65535))
    ACCESS  read-only
    STATUS  mandatory
    DESCRIPTION
        "The entire Link State Advertisement, including
        its header."
    ::= { pf5000Ospfv3LinkLsdbEntry 9 }

--  OSPF Host Table
--    The Host/Metric Table indicates what hosts are directly
--    attached to the Router, and what metrics and types of
--    service should be advertised for them.
--  pf5000Ospfv3 Interface Table

pf5000Ospfv3IfTable OBJECT-TYPE
    SYNTAX  SEQUENCE OF Pf5000Ospfv3IfEntry
    ACCESS  not-accessible
    STATUS  mandatory
    DESCRIPTION
        "The pf5000Ospfv3 Interface Table describes the  inter-
        faces from the viewpoint of pf5000Ospfv3."
    REFERENCE
        "OSPF Version 2, Appendix C.3  Router  interface
        parameters"
    ::= { pf5000Ospfv3 7 }

pf5000Ospfv3IfEntry OBJECT-TYPE
    SYNTAX  Pf5000Ospfv3IfEntry
    ACCESS  not-accessible
    STATUS  mandatory
    DESCRIPTION
        "The pf5000Ospfv3 Interface Entry describes one  inter-
        face from the viewpoint of pf5000Ospfv3."
    INDEX { pf5000Ospfv3IfDomainNumber,
            pf5000Ospfv3IfIndex }
    ::= { pf5000Ospfv3IfTable 1 }

    Pf5000Ospfv3IfEntry ::=
        SEQUENCE {
            pf5000Ospfv3IfDomainNumber
                INTEGER,
            pf5000Ospfv3IfIndex
                INTEGER,
            pf5000Ospfv3IfAreaId
                IpAddress,
            pf5000Ospfv3IfType
                INTEGER,
            pf5000Ospfv3IfAdminStat
                INTEGER,
            pf5000Ospfv3IfRtrPriority
                INTEGER,
            pf5000Ospfv3IfTransitDelay
                INTEGER,
            pf5000Ospfv3IfRetransInterval
                INTEGER,
            pf5000Ospfv3IfHelloInterval
                INTEGER,
            pf5000Ospfv3IfRtrDeadInterval
                INTEGER,
            pf5000Ospfv3IfPollInterval
                INTEGER,
            pf5000Ospfv3IfState
                INTEGER,
            pf5000Ospfv3IfDesignatedRouter
                IpAddress,
            pf5000Ospfv3IfBackupDesignatedRouter
                IpAddress,
            pf5000Ospfv3IfEvents
                Counter,
            pf5000Ospfv3IfStatus
                INTEGER,
            pf5000Ospfv3IfMulticastForwarding
                INTEGER,
            pf5000Ospfv3IfDemand
                INTEGER,
            pf5000Ospfv3IfMetricValue
                INTEGER,
            pf5000Ospfv3IfLinkScopeLsaCount
                INTEGER,
            pf5000Ospfv3IfLinkLsaCksumSum
                INTEGER,
            pf5000Ospfv3IfInstId
                INTEGER
        }

pf5000Ospfv3IfDomainNumber OBJECT-TYPE
    SYNTAX  INTEGER
    ACCESS  read-only
    STATUS  mandatory
    DESCRIPTION
        "ospfv3 domain number."
    ::= { pf5000Ospfv3IfEntry 1 }

pf5000Ospfv3IfIndex OBJECT-TYPE
    SYNTAX  INTEGER
    ACCESS  read-only
    STATUS  mandatory
    DESCRIPTION
        "The interface index of this pf5000Ospfv3 interface.
        It corresponds to the interface index of the
        Ipv6 interface on which pf5000Ospfv3 is configured."
    ::= { pf5000Ospfv3IfEntry 2 }

pf5000Ospfv3IfAreaId OBJECT-TYPE
    SYNTAX  IpAddress
    ACCESS  read-only
    STATUS  mandatory
    DESCRIPTION
        "A 32-bit integer uniquely identifying the area
        to  which  the  interface  connects.   Area  ID
        0.0.0.0 is used for the pf5000Ospfv3 backbone."
    DEFVAL   { '00000000'H }  -- 0.0.0.0
    ::= { pf5000Ospfv3IfEntry 3 }

pf5000Ospfv3IfType OBJECT-TYPE
    SYNTAX  INTEGER {
        broadcast (1),
        nbma (2),
        pointToPoint (3),
        pointToMultipoint (5)
    }
    ACCESS  read-only
    STATUS  mandatory
    DESCRIPTION
        "The pf5000Ospfv3 interface type."
    ::= { pf5000Ospfv3IfEntry 4 }

pf5000Ospfv3IfAdminStat OBJECT-TYPE
    SYNTAX  INTEGER {
        enabled (1),
        disabled (2)
    }
    ACCESS  read-only
    STATUS  mandatory
    DESCRIPTION
        "The pf5000Ospfv3 interface's  administrative  status.
        The  value formed on the interface, and the in-
        terface will be advertised as an internal route
        to  some  area.  The  value 'disabled' denotes
        that the interface is external to pf5000Ospfv3."
    DEFVAL { enabled }
    ::= { pf5000Ospfv3IfEntry 5 }

pf5000Ospfv3IfRtrPriority OBJECT-TYPE
    SYNTAX  INTEGER
    ACCESS  read-only
    STATUS  mandatory
    DESCRIPTION
        "The  priority  of  this  interface.   Used  in
        multi-access  networks,  this  field is used in
        the designated router election algorithm.  The
        value 0 signifies that the router is not eligi-
        ble to become the  designated  router  on  this
        particular  network.   In the event of a tie in
        this value, routers will use their Router ID as
        a tie breaker."
    DEFVAL { 1 }
    ::= { pf5000Ospfv3IfEntry 6 }

pf5000Ospfv3IfTransitDelay OBJECT-TYPE
    SYNTAX  INTEGER
    ACCESS  read-only
    STATUS  mandatory
    DESCRIPTION
        "The estimated number of seconds  it  takes  to
        transmit  a  link state update packet over this
        interface."
    DEFVAL { 1 }
    ::= { pf5000Ospfv3IfEntry 7 }

pf5000Ospfv3IfRetransInterval OBJECT-TYPE
    SYNTAX  INTEGER
    ACCESS  read-only
    STATUS  mandatory
    DESCRIPTION
        "The number of seconds between  link-state  ad-
        vertisement  retransmissions,  for  adjacencies
        belonging to this  interface.  This  value  is
        also used when retransmitting database descrip-
        tion and link-state request packets."
    DEFVAL { 5 }
    ::= { pf5000Ospfv3IfEntry 8 }

pf5000Ospfv3IfHelloInterval OBJECT-TYPE
    SYNTAX  INTEGER
    ACCESS  read-only
    STATUS  mandatory
    DESCRIPTION
        "The length of time, in  seconds,  between  the
        Hello  packets that the router sends on the in-
        terface.  This value must be the same  for  all
        routers attached to a common network."
    DEFVAL { 10 }
    ::= { pf5000Ospfv3IfEntry 9 }

pf5000Ospfv3IfRtrDeadInterval OBJECT-TYPE
    SYNTAX  INTEGER
    ACCESS  read-only
    STATUS  mandatory
    DESCRIPTION
        "The number of seconds that  a  router's  Hello
        packets  have  not been seen before it's neigh-
        bors declare the router down.  This  should  be
        some  multiple  of  the  Hello  interval.  This
        value must be the same for all routers attached
        to a common network."
    DEFVAL { 40 }
    ::= { pf5000Ospfv3IfEntry 10 }

pf5000Ospfv3IfPollInterval OBJECT-TYPE
    SYNTAX  INTEGER
    ACCESS  read-only
    STATUS  mandatory
    DESCRIPTION
        "The larger time interval, in seconds,  between
        the  Hello  packets  sent  to  an inactive non-
        broadcast multi- access neighbor."
    DEFVAL { 120 }
    ::= { pf5000Ospfv3IfEntry 11 }

pf5000Ospfv3IfState OBJECT-TYPE
    SYNTAX  INTEGER {
        down (1),
        loopback (2),
        waiting (3),
        pointToPoint (4),
        designatedRouter (5),
        backupDesignatedRouter (6),
        otherDesignatedRouter (7)
    }
    ACCESS  read-only
    STATUS  mandatory
    DESCRIPTION
        "The pf5000Ospfv3 Interface State."
    DEFVAL { down }
    ::= { pf5000Ospfv3IfEntry 12 }

pf5000Ospfv3IfDesignatedRouter OBJECT-TYPE
    SYNTAX  IpAddress
    ACCESS  read-only
    STATUS  mandatory
    DESCRIPTION
        "The Router ID of the Designated Router."
    DEFVAL  { '00000000'H }  -- 0.0.0.0
    ::= { pf5000Ospfv3IfEntry 13 }

pf5000Ospfv3IfBackupDesignatedRouter OBJECT-TYPE
    SYNTAX  IpAddress
    ACCESS  read-only
    STATUS  mandatory
    DESCRIPTION
        "The  Router ID of  the  Backup   Designated
        Router."
    DEFVAL  { '00000000'H }  -- 0.0.0.0
    ::= { pf5000Ospfv3IfEntry 15 }

pf5000Ospfv3IfEvents OBJECT-TYPE
    SYNTAX  Counter
    ACCESS  read-only
    STATUS  mandatory
    DESCRIPTION
        "The number of times this  OSPF  interface  has
        changed its state, or an error has occurred."
    ::= { pf5000Ospfv3IfEntry 16 }

pf5000Ospfv3IfStatus OBJECT-TYPE
    SYNTAX  INTEGER
    ACCESS  read-only
    STATUS  mandatory
    DESCRIPTION
        "This variable displays the status of  the  en-
        try.  Setting it to 'invalid' has the effect of
        rendering it inoperative.  The internal  effect
        (row removal) is implementation dependent."
    ::= { pf5000Ospfv3IfEntry 18 }

pf5000Ospfv3IfMulticastForwarding OBJECT-TYPE
    SYNTAX  INTEGER {
        blocked (1),   -- no multicast forwarding
        multicast (2), -- using multicast address
        unicast (3)    -- to each pf5000Ospfv3 neighbor
    }
    ACCESS  read-only
    STATUS  mandatory
    DESCRIPTION
        "The way multicasts should  forwarded  on  this
        interface;  not  forwarded,  forwarded  as data
        link multicasts, or forwarded as data link uni-
        casts.  Data link multicasting is not meaning-
        ful on point to point and NBMA interfaces, and
        setting pf5000Ospfv3MulticastForwarding to 0 effective-
        ly disables all multicast forwarding."
    DEFVAL { blocked }
    ::= { pf5000Ospfv3IfEntry 19 }

pf5000Ospfv3IfDemand OBJECT-TYPE
    SYNTAX  INTEGER {
        true (1),
        false (2)
    }
    ACCESS  read-only
    STATUS  mandatory
    DESCRIPTION
        "Indicates whether Demand pf5000Ospfv3 procedures (hel-
        lo supression to FULL neighbors and setting the
        DoNotAge flag on proogated LSAs) should be per-
        formed on this interface."
    DEFVAL { false }
    ::= { pf5000Ospfv3IfEntry 20 }

pf5000Ospfv3IfMetricValue OBJECT-TYPE
    SYNTAX  INTEGER
    ACCESS  read-only
    STATUS  mandatory
    DESCRIPTION
        "The metric assigned to this interface.
        The default value of the Metric is
        10^8 / ifSpeed."
    ::= { pf5000Ospfv3IfEntry 21 }

pf5000Ospfv3IfLinkScopeLsaCount OBJECT-TYPE
    SYNTAX  INTEGER
    ACCESS  read-only
    STATUS  mandatory
    DESCRIPTION
        "The total number of Link-Scope link-state
        advertisements in  this  link's link-state database."
    ::= { pf5000Ospfv3IfEntry 22 }

pf5000Ospfv3IfLinkLsaCksumSum OBJECT-TYPE
    SYNTAX  INTEGER
    ACCESS  read-only
    STATUS  mandatory
    DESCRIPTION
        "The 32-bit unsigned sum of the Link-Scope link-state
        advertisements'  LS  checksums  contained in this
        link's link-state database.  The sum can be used
        to determine if  there  has been  a  change  in a
        router's link state database, and to compare the
        link-state database of two routers."
    DEFVAL  { 0 }
    ::= { pf5000Ospfv3IfEntry 23 }

pf5000Ospfv3IfInstId OBJECT-TYPE
    SYNTAX  INTEGER
    ACCESS  read-only
    STATUS  mandatory
    DESCRIPTION
        "Enables multiple instances of pf5000Ospfv3 to be run over
        a single link. Each protocol instance would be assigned
        a separate ID. This ID has local link significance
        only."
    DEFVAL  { 0 }
    ::= { pf5000Ospfv3IfEntry 24 }

--  pf5000Ospfv3 Virtual Interface Table
--    The Virtual Interface Table describes the virtual
--    links that the pf5000Ospfv3 Process is configured to
--    carry on.

pf5000Ospfv3VirtIfTable OBJECT-TYPE
    SYNTAX  SEQUENCE OF Pf5000Ospfv3VirtIfEntry
    ACCESS  not-accessible
    STATUS  mandatory
    DESCRIPTION
        "Information about this router's virtual inter-
        faces."
    REFERENCE
        "OSPF Version  2,  Appendix  C.4   Virtual  link
        parameters"
    ::= { pf5000Ospfv3 8 }

pf5000Ospfv3VirtIfEntry OBJECT-TYPE
    SYNTAX  Pf5000Ospfv3VirtIfEntry
    ACCESS  not-accessible
    STATUS  mandatory
    DESCRIPTION
        "Information about a single Virtual Interface."
    INDEX { pf5000Ospfv3VirtIfDomainNumber, pf5000Ospfv3VirtIfAreaId, pf5000Ospfv3VirtIfNeighbor }
    ::= { pf5000Ospfv3VirtIfTable 1 }

    Pf5000Ospfv3VirtIfEntry ::=
        SEQUENCE {
            pf5000Ospfv3VirtIfDomainNumber
                INTEGER,
            pf5000Ospfv3VirtIfAreaId
                IpAddress,
            pf5000Ospfv3VirtIfNeighbor
                IpAddress,
            pf5000Ospfv3VirtIfIndex
                INTEGER,
            pf5000Ospfv3VirtIfTransitDelay
                INTEGER,
            pf5000Ospfv3VirtIfRetransInterval
                INTEGER,
            pf5000Ospfv3VirtIfHelloInterval
                INTEGER,
            pf5000Ospfv3VirtIfRtrDeadInterval
                INTEGER,
            pf5000Ospfv3VirtIfState
                INTEGER,
            pf5000Ospfv3VirtIfEvents
                Counter,
            pf5000Ospfv3VirtIfStatus
                INTEGER,
            pf5000Ospfv3VirtIfLinkScopeLsaCount
                INTEGER,
            pf5000Ospfv3VirtIfLinkLsaCksumSum
                INTEGER
        }

pf5000Ospfv3VirtIfDomainNumber OBJECT-TYPE
    SYNTAX  INTEGER
    ACCESS  read-only
    STATUS  mandatory
    DESCRIPTION
        "ospfv3 domain number."
    ::= { pf5000Ospfv3VirtIfEntry 1 }

pf5000Ospfv3VirtIfAreaId OBJECT-TYPE
    SYNTAX  IpAddress
    ACCESS  read-only
    STATUS  mandatory
    DESCRIPTION
        "The  Transit  Area  that  the   Virtual   Link
        traverses.  By definition, this is not 0.0.0.0"
    ::= { pf5000Ospfv3VirtIfEntry 2 }

pf5000Ospfv3VirtIfNeighbor OBJECT-TYPE
    SYNTAX  IpAddress
    ACCESS  read-only
    STATUS mandatory
    DESCRIPTION
        "The Router ID of the Virtual Neighbor."
    ::= { pf5000Ospfv3VirtIfEntry 3 }

pf5000Ospfv3VirtIfIndex OBJECT-TYPE
    SYNTAX  INTEGER
    ACCESS  read-only
    STATUS  mandatory
    DESCRIPTION
        "The interface index of this pf5000Ospfv3 virtual interface.
        It must be unique among all the interface indices
        on the router."
        ::= { pf5000Ospfv3VirtIfEntry 4 }

pf5000Ospfv3VirtIfTransitDelay OBJECT-TYPE
    SYNTAX  INTEGER
    ACCESS  read-only
    STATUS  mandatory
    DESCRIPTION
        "The estimated number of seconds  it  takes  to
        transmit  a link- state update packet over this
        interface."
    DEFVAL { 1 }
    ::= { pf5000Ospfv3VirtIfEntry 5 }

pf5000Ospfv3VirtIfRetransInterval OBJECT-TYPE
    SYNTAX  INTEGER
    ACCESS  read-only
    STATUS  mandatory
    DESCRIPTION
        "The number of seconds between  link-state  ad-
        vertisement  retransmissions,  for  adjacencies
        belonging to this  interface.  This  value  is
        also used when retransmitting database descrip-
        tion  and  link-state  request  packets.   This
        value  should  be well over the expected round-
        trip time."
    DEFVAL { 5 }
    ::= { pf5000Ospfv3VirtIfEntry 6 }

pf5000Ospfv3VirtIfHelloInterval OBJECT-TYPE
    SYNTAX  INTEGER
    ACCESS  read-only
    STATUS  mandatory
    DESCRIPTION
        "The length of time, in  seconds,  between  the
        Hello  packets that the router sends on the in-
        terface.  This value must be the same  for  the
        virtual neighbor."
    DEFVAL { 10 }
    ::= { pf5000Ospfv3VirtIfEntry 7 }

pf5000Ospfv3VirtIfRtrDeadInterval OBJECT-TYPE
    SYNTAX  INTEGER
    ACCESS  read-only
    STATUS  mandatory
    DESCRIPTION
        "The number of seconds that  a  router's  Hello
        packets  have  not been seen before it's neigh-
        bors declare the router down.  This  should  be
        some  multiple  of  the  Hello  interval.  This
        value must be the same for the  virtual  neigh-
        bor."
    DEFVAL { 60 }
    ::= { pf5000Ospfv3VirtIfEntry 8 }

pf5000Ospfv3VirtIfState OBJECT-TYPE
    SYNTAX  INTEGER {
        down (1),    -- these use the same encoding
        pointToPoint (4) -- as the pf5000Ospfv3IfTable
    }
    ACCESS  read-only
    STATUS  mandatory
    DESCRIPTION
        "OSPF virtual interface states."
    DEFVAL  { down }
    ::= { pf5000Ospfv3VirtIfEntry 9 }

pf5000Ospfv3VirtIfEvents OBJECT-TYPE
    SYNTAX  Counter
    ACCESS  read-only
    STATUS  mandatory
    DESCRIPTION
        "The number of state changes or error events on
        this Virtual Link"
    ::= { pf5000Ospfv3VirtIfEntry 10 }

pf5000Ospfv3VirtIfStatus OBJECT-TYPE
    SYNTAX  INTEGER
    ACCESS  read-only
    STATUS  mandatory
    DESCRIPTION
        "This variable displays the status of  the  en-
        try.  Setting it to 'invalid' has the effect of
        rendering it inoperative.  The internal  effect
        (row removal) is implementation dependent."
        ::= { pf5000Ospfv3VirtIfEntry 11 }

pf5000Ospfv3VirtIfLinkScopeLsaCount OBJECT-TYPE
    SYNTAX  INTEGER
    ACCESS  read-only
    STATUS  mandatory
    DESCRIPTION
        "The total number of Link-Scope link-state
        advertisements in  this  virtual link's link-state
        database."
    ::= { pf5000Ospfv3VirtIfEntry 12 }

pf5000Ospfv3VirtIfLinkLsaCksumSum OBJECT-TYPE
    SYNTAX  INTEGER
    ACCESS  read-only
    STATUS  mandatory
    DESCRIPTION
        "The 32-bit unsigned sum of the Link-Scope link-state
        advertisements'  LS  checksums  contained in this
        virtual link's link-state database.  The sum can be used
        to determine if  there  has been  a  change  in a
        router's link state database, and to compare the
        link-state database of two routers."
    DEFVAL  { 0 }
    ::= { pf5000Ospfv3VirtIfEntry 13 }

--  pf5000Ospfv3 Neighbor Table
--    The pf5000Ospfv3 Neighbor Table describes all neighbors in
--    the locality of the subject router.

pf5000Ospfv3NbrTable OBJECT-TYPE
    SYNTAX  SEQUENCE OF Pf5000Ospfv3NbrEntry
    ACCESS  not-accessible
    STATUS  mandatory
    DESCRIPTION
        "A table of non-virtual neighbor information."
    REFERENCE
        "OSPF Version 2, Section 10  The  Neighbor  Data
        Structure"
    ::= { pf5000Ospfv3 9 }

pf5000Ospfv3NbrEntry OBJECT-TYPE
    SYNTAX  Pf5000Ospfv3NbrEntry
    ACCESS  not-accessible
    STATUS  mandatory
    DESCRIPTION
        "The information regarding a single neighbor."
    REFERENCE
        "OSPF Version 2, Section 10  The  Neighbor  Data
        Structure"
    INDEX { pf5000Ospfv3NbrDomainNumber, pf5000Ospfv3NbrIfIndex, pf5000Ospfv3NbrIpv6Addr }
    ::= { pf5000Ospfv3NbrTable 1 }

    Pf5000Ospfv3NbrEntry ::=
        SEQUENCE {
            pf5000Ospfv3NbrDomainNumber
                INTEGER,
            pf5000Ospfv3NbrIfIndex
                INTEGER,
            pf5000Ospfv3NbrIpv6Addr
                Ipv6Address,
            pf5000Ospfv3NbrRtrId
                IpAddress,
            pf5000Ospfv3NbrOptions
                INTEGER,
            pf5000Ospfv3NbrPriority
                INTEGER,
            pf5000Ospfv3NbrState
                INTEGER,
            pf5000Ospfv3NbrEvents
                Counter,
            pf5000Ospfv3NbrLsRetransQLen
                Gauge,
            pf5000Ospfv3NbrHelloSuppressed
                INTEGER,
            pf5000Ospfv3NbrIfId
                INTEGER
        }

pf5000Ospfv3NbrDomainNumber OBJECT-TYPE
    SYNTAX  INTEGER
    ACCESS  read-only
    STATUS  mandatory
    DESCRIPTION
        "ospfv3 domain number."
    ::= { pf5000Ospfv3NbrEntry 1 }

pf5000Ospfv3NbrIfIndex OBJECT-TYPE
    SYNTAX  INTEGER
    ACCESS  read-only
    STATUS  mandatory
    DESCRIPTION
        "The local link ID of the link over which the
        neighbor can be reached."
    ::= { pf5000Ospfv3NbrEntry 2 }

pf5000Ospfv3NbrIpv6Addr OBJECT-TYPE
    SYNTAX  Ipv6Address
    ACCESS  read-only
    STATUS  mandatory
    DESCRIPTION
        "The IPv6 address of the neighbor associated with
        the local link."
    ::= { pf5000Ospfv3NbrEntry 3 }

pf5000Ospfv3NbrRtrId OBJECT-TYPE
    SYNTAX  IpAddress
    ACCESS  read-only
    STATUS  mandatory
    DESCRIPTION
        "A 32-bit integer (represented as a type  IpAd-
        dress)  uniquely  identifying  the  neighboring
        router in the Autonomous System."
    ::= { pf5000Ospfv3NbrEntry 4 }

pf5000Ospfv3NbrOptions OBJECT-TYPE
    SYNTAX  INTEGER
    ACCESS  read-only
    STATUS  mandatory
    DESCRIPTION
        "A Bit Mask corresponding to the neighbor's op-
        tions field."
    DEFVAL { 0 }
    ::= { pf5000Ospfv3NbrEntry 5 }

pf5000Ospfv3NbrPriority OBJECT-TYPE
    SYNTAX  INTEGER
    ACCESS  read-only
    STATUS  mandatory
    DESCRIPTION
        "The priority of this neighbor in the designat-
        ed router election algorithm.  The value 0 sig-
        nifies that the neighbor is not eligible to be-
        come  the  designated router on this particular
        network."
    DEFVAL { 1 }
    ::= { pf5000Ospfv3NbrEntry 6 }

pf5000Ospfv3NbrState OBJECT-TYPE
    SYNTAX  INTEGER {
        down (1),
        attempt (2),
        init (3),
        twoWay (4),
        exchangeStart (5),
        exchange (6),
        loading (7),
        full (8)
    }
    ACCESS  read-only
    STATUS  mandatory
    DESCRIPTION
        "The State of the relationship with this Neigh-
        bor."
    REFERENCE
        "OSPF Version 2, Section 10.1 Neighbor States"
    DEFVAL  { down }
    ::= { pf5000Ospfv3NbrEntry 7 }

pf5000Ospfv3NbrEvents OBJECT-TYPE
    SYNTAX  Counter
    ACCESS  read-only
    STATUS  mandatory
    DESCRIPTION
        "The number of times this neighbor relationship
        has changed state, or an error has occurred."
    ::= { pf5000Ospfv3NbrEntry 8 }

pf5000Ospfv3NbrLsRetransQLen OBJECT-TYPE
    SYNTAX  Gauge
    ACCESS  read-only
    STATUS  mandatory
    DESCRIPTION
        "The  current  length  of  the   retransmission
        queue."
    ::= { pf5000Ospfv3NbrEntry 9 }

pf5000Ospfv3NbrHelloSuppressed OBJECT-TYPE
    SYNTAX  INTEGER
    ACCESS  read-only
    STATUS  mandatory
    DESCRIPTION
        "Indicates whether Hellos are being  suppressed
        to the neighbor"
    ::= { pf5000Ospfv3NbrEntry 12 }

pf5000Ospfv3NbrIfId OBJECT-TYPE
    SYNTAX  INTEGER
    ACCESS  read-only
    STATUS  mandatory
    DESCRIPTION
        "The interface ID that the neighbor advertises
        in its Hello Packets on this link, that is, the
        neighbor's local interface index."
    ::= { pf5000Ospfv3NbrEntry 13 }

--  pf5000Ospfv3 Virtual Neighbor Table
--    This table describes all virtual neighbors.
--    Since Virtual Links are configured in the
--    virtual interface table, this table is read-only.

pf5000Ospfv3VirtNbrTable OBJECT-TYPE
    SYNTAX  SEQUENCE OF Pf5000Ospfv3VirtNbrEntry
    ACCESS  not-accessible
    STATUS  mandatory
    DESCRIPTION
        "A table of virtual neighbor information."
    REFERENCE
        "OSPF Version 2, Section 15  Virtual Links"
    ::= { pf5000Ospfv3 10 }

pf5000Ospfv3VirtNbrEntry OBJECT-TYPE
    SYNTAX  Pf5000Ospfv3VirtNbrEntry
    ACCESS  not-accessible
    STATUS  mandatory
    DESCRIPTION
        "Virtual neighbor information."
    INDEX { pf5000Ospfv3VirtNbrDomainNumber, pf5000Ospfv3VirtNbrArea, pf5000Ospfv3VirtNbrRtrId }
    ::= { pf5000Ospfv3VirtNbrTable 1 }

    Pf5000Ospfv3VirtNbrEntry ::=
        SEQUENCE {
            pf5000Ospfv3VirtNbrDomainNumber
                INTEGER,
            pf5000Ospfv3VirtNbrArea
                IpAddress,
            pf5000Ospfv3VirtNbrRtrId
                IpAddress,
            pf5000Ospfv3VirtNbrIfIndex
                INTEGER,
            pf5000Ospfv3VirtNbrIpv6Addr
                Ipv6Address,
            pf5000Ospfv3VirtNbrOptions
                INTEGER,
            pf5000Ospfv3VirtNbrState
                INTEGER,
            pf5000Ospfv3VirtNbrEvents
                Counter,
            pf5000Ospfv3VirtNbrLsRetransQLen
                Gauge,
            pf5000Ospfv3VirtNbrHelloSuppressed
                INTEGER,
            pf5000Ospfv3VirtNbrIfId
                INTEGER
        }

pf5000Ospfv3VirtNbrDomainNumber OBJECT-TYPE
    SYNTAX  INTEGER
    ACCESS  read-only
    STATUS  mandatory
    DESCRIPTION
        "ospfv3 domain number."
    ::= { pf5000Ospfv3VirtNbrEntry 1 }

pf5000Ospfv3VirtNbrArea OBJECT-TYPE
    SYNTAX  IpAddress
    ACCESS  read-only
    STATUS  mandatory
    DESCRIPTION
        "The Transit Area Identifier."
    ::= { pf5000Ospfv3VirtNbrEntry 2 }

pf5000Ospfv3VirtNbrRtrId OBJECT-TYPE
    SYNTAX  IpAddress
    ACCESS  read-only
    STATUS  mandatory
    DESCRIPTION
        "A  32-bit  integer  uniquely  identifying  the
        neighboring router in the Autonomous System."
    ::= { pf5000Ospfv3VirtNbrEntry 3 }

pf5000Ospfv3VirtNbrIfIndex OBJECT-TYPE
    SYNTAX  INTEGER
    ACCESS  read-only
    STATUS  mandatory
    DESCRIPTION
        "The local link ID for the virtual link over
        which the neighbor can be reached."
    ::= { pf5000Ospfv3VirtNbrEntry 4 }

pf5000Ospfv3VirtNbrIpv6Addr OBJECT-TYPE
    SYNTAX  Ipv6Address
    ACCESS  read-only
    STATUS  mandatory
    DESCRIPTION
        "The IPv6 address used to reach this Virtual Neighbor.
        It must be a Site-Local or Global scope address."
    ::= { pf5000Ospfv3VirtNbrEntry 5 }

pf5000Ospfv3VirtNbrOptions OBJECT-TYPE
    SYNTAX  INTEGER
    ACCESS  read-only
    STATUS  mandatory
    DESCRIPTION
        "A Bit Mask corresponding to the neighbor's op-
        tions field."
    ::= { pf5000Ospfv3VirtNbrEntry 6 }

pf5000Ospfv3VirtNbrState OBJECT-TYPE
    SYNTAX  INTEGER {
        down (1),
        attempt (2),
        init (3),
        twoWay (4),
        exchangeStart (5),
        exchange (6),
        loading (7),
        full (8)
    }
    ACCESS  read-only
    STATUS  mandatory
    DESCRIPTION
        "The state of the  Virtual  Neighbor  Relation-
        ship."
    ::= { pf5000Ospfv3VirtNbrEntry 7 }

pf5000Ospfv3VirtNbrEvents OBJECT-TYPE
    SYNTAX  Counter
    ACCESS  read-only
    STATUS  mandatory
    DESCRIPTION
        "The number of  times  this  virtual  link  has
        changed its state, or an error has occurred."
    ::= { pf5000Ospfv3VirtNbrEntry 8 }

pf5000Ospfv3VirtNbrLsRetransQLen OBJECT-TYPE
    SYNTAX  Gauge
    ACCESS  read-only
    STATUS  mandatory
    DESCRIPTION
        "The  current  length  of  the   retransmission
        queue."
    ::= { pf5000Ospfv3VirtNbrEntry 9 }

pf5000Ospfv3VirtNbrHelloSuppressed OBJECT-TYPE
    SYNTAX  INTEGER
    ACCESS  read-only
    STATUS  mandatory
    DESCRIPTION
        "Indicates whether Hellos are being  suppressed
        to the neighbor"
    ::= { pf5000Ospfv3VirtNbrEntry 10 }

pf5000Ospfv3VirtNbrIfId OBJECT-TYPE
    SYNTAX  INTEGER
    ACCESS  read-only
    STATUS  mandatory
    DESCRIPTION
        "The interface ID that the neighbor advertises
        in its Hello Packets on this virtual link, that is,
        the neighbor's local interface index."
    ::= { pf5000Ospfv3VirtNbrEntry 11 }

 --
 --    The pf5000Ospfv3 Area Aggregate Table
 --

pf5000Ospfv3AreaAggregateTable OBJECT-TYPE
    SYNTAX  SEQUENCE OF Pf5000Ospfv3AreaAggregateEntry
    ACCESS  not-accessible
    STATUS  mandatory
    DESCRIPTION
        "A range of IPv6 prefixes specified by a
        prefix/prefix length  pair. Note that if
        ranges are configured such that one range sub-
        sumes  another range the most specific match is
        the preferred one."
    ::= { pf5000Ospfv3 11 }

pf5000Ospfv3AreaAggregateEntry OBJECT-TYPE
    SYNTAX  Pf5000Ospfv3AreaAggregateEntry
    ACCESS  not-accessible
    STATUS  mandatory
    DESCRIPTION
        "A range of IPv6 prefixes specified by a
        prefix/prefix length  pair. Note that if
        ranges are configured such that one range sub-
        sumes  another range the most specific match is
        the preferred one."
    REFERENCE
        "OSPF Version 2, Appendix C.2  Area parameters"
    INDEX { pf5000Ospfv3AreaAggregateDomainNumber,
            pf5000Ospfv3AreaAggregateAreaID,
            pf5000Ospfv3AreaAggregateAreaLsdbType,
            pf5000Ospfv3AreaAggregateIndex }
    ::= { pf5000Ospfv3AreaAggregateTable 1 }

    Pf5000Ospfv3AreaAggregateEntry ::=
        SEQUENCE {
            pf5000Ospfv3AreaAggregateDomainNumber
                INTEGER,
            pf5000Ospfv3AreaAggregateAreaID
                IpAddress,
            pf5000Ospfv3AreaAggregateAreaLsdbType
                INTEGER,
            pf5000Ospfv3AreaAggregateIndex
                INTEGER,
            pf5000Ospfv3AreaAggregatePrefix
                Ipv6Address,
            pf5000Ospfv3AreaAggregatePrefixLen
                INTEGER,
            pf5000Ospfv3AreaAggregateStatus
                INTEGER,
            pf5000Ospfv3AreaAggregateEffect
                INTEGER
        }

pf5000Ospfv3AreaAggregateDomainNumber OBJECT-TYPE
    SYNTAX  INTEGER
    ACCESS  read-only
    STATUS  mandatory
    DESCRIPTION
        "ospfv3 domain number."
    ::= { pf5000Ospfv3AreaAggregateEntry 1 }

pf5000Ospfv3AreaAggregateAreaID OBJECT-TYPE
    SYNTAX  IpAddress
    ACCESS  read-only
    STATUS  mandatory
    DESCRIPTION
        "The Area the Address Aggregate is to be  found
        within."
    REFERENCE
        "OSPF Version 2, Appendix C.2 Area parameters"
    ::= { pf5000Ospfv3AreaAggregateEntry 2 }

pf5000Ospfv3AreaAggregateAreaLsdbType OBJECT-TYPE
    SYNTAX  INTEGER {
        interAreaPrefixLsa (8195), -- 0x2003
        nssaExternalLsa    (8199)  -- 0x2007
    }
    ACCESS  read-only
    STATUS  mandatory
    DESCRIPTION
        "The type of the Address Aggregate.  This field
        specifies  the  Area Lsdb type that this Address Ag-
        gregate applies to."
    REFERENCE
        "OSPF Version 2, Appendix A.4.1 The  Link  State
        Advertisement header"
    ::= { pf5000Ospfv3AreaAggregateEntry 3 }

pf5000Ospfv3AreaAggregateIndex OBJECT-TYPE
    SYNTAX  INTEGER (1..2147483647)
    ACCESS  read-only
    STATUS  mandatory
    DESCRIPTION
        "A unique identifier for this aggregate table entry."
    ::= { pf5000Ospfv3AreaAggregateEntry 4 }

pf5000Ospfv3AreaAggregatePrefix OBJECT-TYPE
    SYNTAX  Ipv6Address
    ACCESS  read-only
    STATUS  mandatory
    DESCRIPTION
        "The IPv6 Prefix."
    REFERENCE
        "OSPF Version 2, Appendix C.2 Area parameters"
    ::= { pf5000Ospfv3AreaAggregateEntry 5 }

pf5000Ospfv3AreaAggregatePrefixLen OBJECT-TYPE
    SYNTAX  INTEGER ( 3..128 )
--    UNITS  "bits"
    ACCESS  read-only
    STATUS  mandatory
    DESCRIPTION
        "The length of the prefix (in bits). A prefix can
        not be shorter than 3 bits."
    REFERENCE
        "OSPF Version 2, Appendix C.2 Area parameters"
    ::= { pf5000Ospfv3AreaAggregateEntry 6 }

pf5000Ospfv3AreaAggregateStatus OBJECT-TYPE
    SYNTAX  INTEGER
    ACCESS  read-only
    STATUS  mandatory
    DESCRIPTION
        "This variable displays the status of  the  en-
        try.  Setting it to 'invalid' has the effect of
        rendering it inoperative.  The internal  effect
        (row removal) is implementation dependent."
    ::= { pf5000Ospfv3AreaAggregateEntry 7 }

pf5000Ospfv3AreaAggregateEffect OBJECT-TYPE
    SYNTAX  INTEGER {
        advertiseMatching (1),
        doNotAdvertiseMatching (2)
    }
    ACCESS  read-only
    STATUS  mandatory
    DESCRIPTION
        "Prefixes subsumed by ranges either trigger  the
        advertisement  of  the indicated aggregate (ad-
        vertiseMatching), or result in the prefix not
        being advertised at all outside the area."
    DEFVAL  { advertiseMatching }
    ::= { pf5000Ospfv3AreaAggregateEntry 8 }

--  pf5000Login

pf5000LoginName OBJECT-TYPE
    SYNTAX  DisplayString
    ACCESS  not-accessible
    STATUS  mandatory
    DESCRIPTION
        "Log in user name."
    ::= { pf5000Login 1 }

pf5000LoginTime OBJECT-TYPE
    SYNTAX  DisplayString
    ACCESS  not-accessible
    STATUS  mandatory
    DESCRIPTION
        "Date, time and time zone of user log in.
                 Format : YYYY/MM/DD hh:mm:ss XXXXXX(time zone)
         Time zone format :
           JST    : JST
                   GMT+09 : GMT + 09 hours
                   GMT+10 : GMT + 10 hours"
    ::= { pf5000Login 2 }

pf5000LogoutTime OBJECT-TYPE
    SYNTAX  DisplayString
    ACCESS  not-accessible
    STATUS  mandatory
    DESCRIPTION
        "Date, time and time zone of user log out.
        Format : YYYY/MM/DD hh:mm:ss XXXXXX(time zone)
        Time zone format :
          JST    : JST
          GMT+09 : GMT + 09 hours
          GMT+10 : GMT + 10 hours"
    ::= { pf5000Login 3 }

pf5000LoginFailureTime OBJECT-TYPE
    SYNTAX  DisplayString
    ACCESS  not-accessible
    STATUS  mandatory
    DESCRIPTION
        "Date, time and time zone of user log in failure.
        Format : YYYY/MM/DD hh:mm:ss XXXXXX(time zone)
        Time zone format :
          JST    : JST
          GMT+09 : GMT + 09 hours
          GMT+10 : GMT + 10 hours"
    ::= { pf5000Login 4 }

pf5000LoginLocation OBJECT-TYPE
    SYNTAX  DisplayString
    ACCESS  not-accessible
    STATUS  mandatory
    DESCRIPTION
        "Terminal information of log in user.
        The status will be 'console' or 'aux'.
        If other, displays 'TERMINAL(APLLICATION)'.
        ex. 'tty/1(telnet)'"
    ::= { pf5000Login 5 }

pf5000LoginLine OBJECT-TYPE
    SYNTAX  DisplayString
    ACCESS  not-accessible
    STATUS  mandatory
    DESCRIPTION
        "Connection information of log in user.
        The status will be 'console' or 'aux'.
        If other, displays 'IPADDRESS(APLLICATION)'.
        ex. '192.168.11.1(telnet)'"
    ::= { pf5000Login 6 }

pf5000LogoutStatus OBJECT-TYPE
    SYNTAX  INTEGER {
        error(1),
        success(2),
        timeout(3),
        disconnect(4),
        force(5)
    }
    ACCESS  not-accessible
    STATUS  mandatory
    DESCRIPTION
        "Log out factor.
         error(1)      : log out due to none of bellow
         success(2)    : log out due to command
         timeout(3)    : log out due to 'auto-logout'
         disconnect(4) : log out due to line disconnection
         force(5)      : log out due to other user's command"
    ::= { pf5000Login 7 }

--  pf5000Axrp group 

pf5000AxrpGroupTable OBJECT-TYPE
    SYNTAX  SEQUENCE OF Pf5000AxrpGroupEntry
    ACCESS  not-accessible
    STATUS  mandatory
    DESCRIPTION
        "The table containing AXRP group information."
    ::= { pf5000Axrp 1 }

pf5000AxrpGroupEntry OBJECT-TYPE
    SYNTAX  Pf5000AxrpGroupEntry
    ACCESS  not-accessible
    STATUS  mandatory
    DESCRIPTION
        "The list of AXRP group information."
    INDEX { pf5000AxrpGroupRingId }
    ::= { pf5000AxrpGroupTable 1 }

    Pf5000AxrpGroupEntry ::=
        SEQUENCE {
        pf5000AxrpGroupRingId
            INTEGER,
        pf5000AxrpGroupRowStatus
            RowStatus,
        pf5000AxrpGroupMode
            INTEGER,
        pf5000AxrpGroupRingAttribute
            INTEGER,
        pf5000AxrpGroupMonitoringState
            INTEGER,
        pf5000AxrpGroupRingport1
            INTEGER,
        pf5000AxrpGroupRingport1Shared
            INTEGER,
        pf5000AxrpGroupRingport2
            INTEGER,
        pf5000AxrpGroupRingport2Shared
            INTEGER,
        pf5000AxrpGroupTransitionToFaultCounts
            Counter,
        pf5000AxrpGroupTransitionToNormalCounts
            Counter,
        pf5000AxrpGroupLastTransitionTime
            TimeStamp
    }

pf5000AxrpGroupRingId OBJECT-TYPE
    SYNTAX  INTEGER
    ACCESS  not-accessible
    STATUS  mandatory
    DESCRIPTION
        "AXRP group ring identifier."
    ::= { pf5000AxrpGroupEntry 1 }

pf5000AxrpGroupRowStatus OBJECT-TYPE
    SYNTAX  RowStatus
    ACCESS  read-only
    STATUS  mandatory
    DESCRIPTION
        "Valid/Invalid state of this entry. Valid(1) fixed"
    ::= { pf5000AxrpGroupEntry 2 }

pf5000AxrpGroupMode OBJECT-TYPE
    SYNTAX  INTEGER {
        no-config(1),
        master(2),
        transit(3)
    }
    ACCESS  read-only
    STATUS  mandatory
    DESCRIPTION
        "Operation mode of each ring ID."
    ::= { pf5000AxrpGroupEntry 3 }

pf5000AxrpGroupRingAttribute OBJECT-TYPE
    SYNTAX  INTEGER {
        no-config(1),
        rift-ring(2),
        rift-ring-edge1(3),
        rift-ring-edge2(4)
    }
    ACCESS  read-only
    STATUS  mandatory
    DESCRIPTION
        "When the multi ring is composed, it is an attribute of this device in the common link non-watch ring. "
    ::= { pf5000AxrpGroupEntry 4 }

pf5000AxrpGroupMonitoringState OBJECT-TYPE
    SYNTAX  INTEGER {
        init(1),
        disable(2),
        fault-monitoring(3),
        recovery-monitoring(4),
        flush-monitoring(5),
        not-operating(6),
        suppress-fault-recovery(7),
        preempt-delay(8),
        monitoring-recovery(9)
    }
    ACCESS  read-only
    STATUS  mandatory
    DESCRIPTION
        "Operation and state of watch of ring. "
    ::= { pf5000AxrpGroupEntry 5 }

pf5000AxrpGroupRingport1 OBJECT-TYPE
    SYNTAX  INTEGER
    ACCESS  read-only
    STATUS  mandatory
    DESCRIPTION
        "IfIndex of ring port 1 (port in one where Ifindex is small)"
    ::= { pf5000AxrpGroupEntry 6 }

pf5000AxrpGroupRingport1Shared OBJECT-TYPE
    SYNTAX  INTEGER {
        no-config(1),
        shared-edge(2),
        shared(3)
    }
    ACCESS  read-only
    STATUS  mandatory
    DESCRIPTION
        "Ring port 1 is common port information. "
    ::= { pf5000AxrpGroupEntry 7 }

pf5000AxrpGroupRingport2 OBJECT-TYPE
    SYNTAX  INTEGER
    ACCESS  read-only
    STATUS  mandatory
    DESCRIPTION
        "IfIndex of ring port 2 (port in one where Ifindex is large)"
    ::= { pf5000AxrpGroupEntry 8 }

pf5000AxrpGroupRingport2Shared OBJECT-TYPE
    SYNTAX  INTEGER {
        no-config(1),
        shared-edge(2),
        shared(3)
    }
    ACCESS  read-only
    STATUS  mandatory
    DESCRIPTION
        "Ring port 2 is common port information."
    ::= { pf5000AxrpGroupEntry 9 }

pf5000AxrpGroupTransitionToFaultCounts OBJECT-TYPE
    SYNTAX  Counter
    ACCESS  read-only
    STATUS  mandatory
    DESCRIPTION
        "Frequency that shifts from state of trouble watch in state of restoration watch. "
    ::= { pf5000AxrpGroupEntry 10 }

pf5000AxrpGroupTransitionToNormalCounts OBJECT-TYPE
    SYNTAX  Counter
    ACCESS  read-only
    STATUS  mandatory
    DESCRIPTION
        "Frequency that shifts from state of restoration watch in state of trouble watch. "
    ::= { pf5000AxrpGroupEntry 11 }

pf5000AxrpGroupLastTransitionTime OBJECT-TYPE
    SYNTAX  TimeStamp
    ACCESS  read-only
    STATUS  mandatory
    DESCRIPTION
        "It is changing the final time to restoration from the trouble or the trouble from restoration. "
    ::= { pf5000AxrpGroupEntry 12 }

pf5000AxrpVlanGroupTable OBJECT-TYPE
    SYNTAX  SEQUENCE OF Pf5000AxrpVlanGroupEntry
    ACCESS  not-accessible
    STATUS  mandatory
    DESCRIPTION
        "The table containing AXRP VLAN group information."
    ::= { pf5000Axrp  2 }

pf5000AxrpVlanGroupEntry OBJECT-TYPE
    SYNTAX  Pf5000AxrpVlanGroupEntry
    ACCESS  not-accessible
    STATUS  mandatory
    DESCRIPTION
        "The list of AXRP VLAN group information."
    INDEX { pf5000AxrpVlanGroupRingId, pf5000AxrpVlanGroupId }
    ::= { pf5000AxrpVlanGroupTable 1 }

    Pf5000AxrpVlanGroupEntry ::=
        SEQUENCE {
            pf5000AxrpVlanGroupRingId                  INTEGER,
            pf5000AxrpVlanGroupId                      INTEGER,
            pf5000AxrpVlanGroupRingport1               INTEGER,
            pf5000AxrpVlanGroupRingport1Role           INTEGER,
            pf5000AxrpVlanGroupRingport1OperState      INTEGER,
            pf5000AxrpVlanGroupRingport2               INTEGER,
            pf5000AxrpVlanGroupRingport2Role           INTEGER,
            pf5000AxrpVlanGroupRingport2OperState      INTEGER
        }

pf5000AxrpVlanGroupRingId OBJECT-TYPE
    SYNTAX  INTEGER
    ACCESS  not-accessible
    STATUS  mandatory
    DESCRIPTION
        "AXRP VLAN ring group number(1~8)"
    ::= { pf5000AxrpVlanGroupEntry  1 }

pf5000AxrpVlanGroupId OBJECT-TYPE
    SYNTAX  INTEGER
    ACCESS  not-accessible
    STATUS  mandatory
    DESCRIPTION
        "AXRP VLAN group number(1~8)"
    ::= { pf5000AxrpVlanGroupEntry  2 }

pf5000AxrpVlanGroupRingport1 OBJECT-TYPE
    SYNTAX  INTEGER
    ACCESS  read-only
    STATUS  mandatory
    DESCRIPTION
        "IfIndex of ring port 1 (port in one where Ifindex is small)"
    ::= { pf5000AxrpVlanGroupEntry 3 }

pf5000AxrpVlanGroupRingport1Role OBJECT-TYPE
    SYNTAX  INTEGER {
        primary(1),
        secondary(2),
        other(3)
    }
    ACCESS  read-only
    STATUS  mandatory
    DESCRIPTION
        "Role of ring port 1"
    ::= { pf5000AxrpVlanGroupEntry 4 }

pf5000AxrpVlanGroupRingport1OperState OBJECT-TYPE
    SYNTAX  INTEGER {
        forwarding(1),
        blocking(2),
        other(3),
        down(4)
    }
    ACCESS  read-only
    STATUS  mandatory
    DESCRIPTION
        "Present of ring port 1"
    ::= { pf5000AxrpVlanGroupEntry 5 }

pf5000AxrpVlanGroupRingport2 OBJECT-TYPE
    SYNTAX  INTEGER
    ACCESS  read-only
    STATUS  mandatory
    DESCRIPTION
        "IfIndex of ring port 2 (port in one where Ifindex is small)"
    ::= { pf5000AxrpVlanGroupEntry 6 }

pf5000AxrpVlanGroupRingport2Role OBJECT-TYPE
    SYNTAX  INTEGER {
        primary(1),
        secondary(2),
        other(3)
    }
    ACCESS  read-only
    STATUS  mandatory
    DESCRIPTION
        "Role of ring port 2"
    ::= { pf5000AxrpVlanGroupEntry 7 }

pf5000AxrpVlanGroupRingport2OperState OBJECT-TYPE
    SYNTAX  INTEGER {
        forwarding(1),
        blocking(2),
        other(3),
        down(4)
    }
    ACCESS  read-only
    STATUS  mandatory
    DESCRIPTION
        "Present of ring port 2"
    ::= { pf5000AxrpVlanGroupEntry 8 }

--  pf5000BootManagement group

pf5000BootReason  OBJECT-TYPE
    SYNTAX  INTEGER {
        power-on(1),
        reload(2),
        system-fault(3),
        system-stall(4),
        reset(5),
        fail-over(6),
        default-restart(7),
        wakeonlan(8),
        recover-high-temp(9)
    }
    ACCESS  read-only
    STATUS  mandatory
    DESCRIPTION
        "Reason of system start."
    ::= { pf5000BootManagement 1 }

--  pf5000lldp group
--  pf5000lldpConfiguration group

pf5000lldpMessageTxInterval OBJECT-TYPE
    SYNTAX  Integer32
    ACCESS  read-only
    STATUS  mandatory
    DESCRIPTION
        "LDPDU transmitting interval"
    ::= { pf5000lldpConfiguration 1 }

pf5000lldpMessageTxHoldMultiplier OBJECT-TYPE
    SYNTAX  Integer32
    ACCESS  read-only
    STATUS  mandatory
    DESCRIPTION
        "Time coefficient for contiguity equipment to hold about the LLDP frame which this equipment transmitted"
    ::= { pf5000lldpConfiguration 2 }

pf5000lldpPortConfigTable OBJECT-TYPE
    SYNTAX  SEQUENCE OF Pf5000lldpPortConfigEntry
    ACCESS  not-accessible
    STATUS  mandatory
    DESCRIPTION
        "The table about LDPDU transmission"
    ::= { pf5000lldpConfiguration 6 }

pf5000lldpPortConfigEntry OBJECT-TYPE
    SYNTAX  Pf5000lldpPortConfigEntry
    ACCESS  not-accessible
    STATUS  mandatory
    DESCRIPTION
        "The entry about LDPDU transmission"
    INDEX { pf5000lldpPortConfigPortNum }
    ::= { pf5000lldpPortConfigTable 1 }

    Pf5000lldpPortConfigEntry ::=
        SEQUENCE {
            pf5000lldpPortConfigPortNum        INTEGER,
            pf5000lldpPortConfigAdminStatus    INTEGER,
            pf5000lldpPortConfigTLVsTxEnable   BITS,
            pf5000lldpPortConfigRowStatus      RowStatus
        }

pf5000lldpPortConfigPortNum OBJECT-TYPE
    SYNTAX  INTEGER
    ACCESS  not-accessible
    STATUS  mandatory
    DESCRIPTION
        "Port discernment index"
    ::= {pf5000lldpPortConfigEntry 2 }

pf5000lldpPortConfigAdminStatus OBJECT-TYPE
    SYNTAX  INTEGER {
        txOnly(1),
        rxOnly(2),
        txAndRx(3),
        disabled(4)
    }
    ACCESS  read-only
    STATUS  mandatory
    DESCRIPTION
        "The port state of this equipment about transmission and reception of LDPDU"
    ::= {pf5000lldpPortConfigEntry 3 }

pf5000lldpPortConfigTLVsTxEnable OBJECT-TYPE
    SYNTAX  BITS{
        portDesc(4),
        sysName(5),
        sysDesc(6),
        sysCap(7)
    }
    ACCESS  read-only
    STATUS  mandatory
    DESCRIPTION
        "The TLV state about the port concerned which can be transmitted"
    ::= {pf5000lldpPortConfigEntry 4 }

pf5000lldpPortConfigRowStatus OBJECT-TYPE
    SYNTAX  RowStatus
    ACCESS  read-only
    STATUS  mandatory
    DESCRIPTION
        "The state of this entry"
    ::= {pf5000lldpPortConfigEntry 5 }

-- pf5000lldpStats group

pf5000lldpStatsTable OBJECT-TYPE
    SYNTAX  SEQUENCE OF Pf5000lldpStatsEntry
    ACCESS  not-accessible
    STATUS  mandatory
    DESCRIPTION
        "The table about LLDP statistics information"
    ::= { pf5000lldpStats 1 }

pf5000lldpStatsEntry OBJECT-TYPE
    SYNTAX  Pf5000lldpStatsEntry
    ACCESS  not-accessible
    STATUS  mandatory
    DESCRIPTION
        "The Entry about LLDP statistics information"
    INDEX { pf5000lldpStatsPortNum }
    ::= { pf5000lldpStatsTable 1 }

    Pf5000lldpStatsEntry ::=
        SEQUENCE {
            pf5000lldpStatsPortNum             INTEGER,
            pf5000lldpStatsOperStatus          INTEGER,
            pf5000lldpStatsFramesInErrors      Counter32,
            pf5000lldpStatsFramesInTotal       Counter32,
            pf5000lldpStatsFramesOutTotal      Counter32,
            pf5000lldpStatsTLVsInErrors        Counter32,
            pf5000lldpStatsTLVsDiscardedTotal  Counter32
        }

pf5000lldpStatsPortNum OBJECT-TYPE
    SYNTAX  INTEGER
    ACCESS  not-accessible
    STATUS  mandatory
    DESCRIPTION
        "Port discernment index"
    ::= {pf5000lldpStatsEntry 2 }

pf5000lldpStatsOperStatus OBJECT-TYPE
    SYNTAX  INTEGER
    ACCESS  read-only
    STATUS  mandatory
    DESCRIPTION
        "The employment state about the port concerned"
    ::= {pf5000lldpStatsEntry 3 }

pf5000lldpStatsFramesInErrors OBJECT-TYPE
    SYNTAX  Counter32
    ACCESS  read-only
    STATUS  mandatory
    DESCRIPTION
        "The number of inaccurate LDPDU reception about the port concerned"
    ::= {pf5000lldpStatsEntry 4 }

pf5000lldpStatsFramesInTotal OBJECT-TYPE
    SYNTAX  Counter32
    ACCESS  read-only
    STATUS  mandatory
    DESCRIPTION
        "The total number of LDPDU reception about the port concerned"
    ::= {pf5000lldpStatsEntry 5 }

pf5000lldpStatsFramesOutTotal OBJECT-TYPE
    SYNTAX  Counter32
    ACCESS  read-only
    STATUS  mandatory
    DESCRIPTION
        "The total number of LDPDU transmission about the port concerned"
    ::= {pf5000lldpStatsEntry 6 }

pf5000lldpStatsTLVsInErrors OBJECT-TYPE
    SYNTAX  Counter32
    ACCESS  read-only
    STATUS  mandatory
    DESCRIPTION
        "The number of inaccurate TLV reception about the port concerned"
    ::= {pf5000lldpStatsEntry 7 }

pf5000lldpStatsTLVsDiscardedTotal OBJECT-TYPE
    SYNTAX  Counter32
    ACCESS  read-only
    STATUS  mandatory
    DESCRIPTION
        "The total abandonment TLV number about the port concerned"
    ::= {pf5000lldpStatsEntry 8 }

-- pf5000lldpLocalSystemData group

pf5000lldpLocChassisType OBJECT-TYPE
    SYNTAX  INTEGER {
        entPhysicalAlias(1),
        ifAlias(2),
        portEntPhysicalAlias(3),
        backplaneEntPhysicalAlias(4),
        macAddress(5),
        networkAddress(6)
    }
    ACCESS  read-only
    STATUS  mandatory
    DESCRIPTION
        "The chassis type about this equipment"
    ::= {pf5000lldpLocalSystemData 1 }

pf5000lldpLocChassisId OBJECT-TYPE
    SYNTAX  OCTET STRING 
    ACCESS  read-only
    STATUS  mandatory
    DESCRIPTION
        "The chassis ID about this equipment"
    ::= {pf5000lldpLocalSystemData 2 }

pf5000lldpLocSysName OBJECT-TYPE
    SYNTAX  OCTET STRING
    ACCESS  read-only
    STATUS  mandatory
    DESCRIPTION
        "The chassis ID about this equipment"
    ::= {pf5000lldpLocalSystemData 3 }

pf5000lldpLocSysDesc OBJECT-TYPE
    SYNTAX  DisplayString
    ACCESS  read-only
    STATUS  mandatory
    DESCRIPTION
        "System information about this equipment"
    ::= {pf5000lldpLocalSystemData 4 }

pf5000lldpLocPortTable OBJECT-TYPE
    SYNTAX  SEQUENCE OF Pf5000lldpLocPortEntry
    ACCESS  not-accessible
    STATUS  mandatory
    DESCRIPTION
        "The table about the port of this equipment"
    ::= { pf5000lldpLocalSystemData 7 }

pf5000lldpLocPortEntry OBJECT-TYPE
    SYNTAX  Pf5000lldpLocPortEntry
    ACCESS  not-accessible
    STATUS  mandatory
    DESCRIPTION
        "The entry about the port of this equipment"
    INDEX { pf5000lldpLocPortNum }
    ::= { pf5000lldpLocPortTable 1 }

    Pf5000lldpLocPortEntry ::=
        SEQUENCE {
            pf5000lldpLocPortNum       INTEGER,
            pf5000lldpLocPortType      INTEGER,
            pf5000lldpLocPortId        OCTET STRING,
            pf5000lldpLocPortDesc      OCTET STRING
        }

pf5000lldpLocPortNum OBJECT-TYPE
    SYNTAX  INTEGER
    ACCESS  not-accessible
    STATUS  mandatory
    DESCRIPTION
        "Port discernment index"
    ::= {pf5000lldpLocPortEntry 1 }

pf5000lldpLocPortType OBJECT-TYPE
    SYNTAX  INTEGER {
        ifAlias(1),
        portEntPhysicalAlias(2),
        backplaneEntPhysicalAlias(3),
        macAddress(4),
        networkAddress(5),
        local(6)
    }
    ACCESS  read-only
    STATUS  mandatory
    DESCRIPTION
        "The port type about the port concerned of this equipment"
    ::= {pf5000lldpLocPortEntry 2 }

pf5000lldpLocPortId OBJECT-TYPE
    SYNTAX  OCTET STRING
    ACCESS  read-only
    STATUS  mandatory
    DESCRIPTION
        "The port ID about the port concerned of this equipment"
    ::= {pf5000lldpLocPortEntry 3 }

pf5000lldpLocPortDesc OBJECT-TYPE
    SYNTAX  OCTET STRING
    ACCESS  read-only
    STATUS  mandatory
    DESCRIPTION
        "Port information about the port concerned of this equipment"
    ::= {pf5000lldpLocPortEntry 4 }

-- pf5000lldpRemoteSystemData group

pf5000lldpRemTable OBJECT-TYPE
    SYNTAX  SEQUENCE OF Pf5000lldpRemEntry
    ACCESS  not-accessible
    STATUS  mandatory
    DESCRIPTION
        "The table about contiguity equipment"
    ::= { pf5000lldpRemoteSystemData 1 }

pf5000lldpRemEntry OBJECT-TYPE
    SYNTAX  Pf5000lldpRemEntry
    ACCESS  not-accessible
    STATUS  mandatory
    DESCRIPTION
        "The entry about contiguity equipment"
    INDEX { pf5000lldpRemLocalPortNum,pf5000lldpRemIndex }
    ::= { pf5000lldpRemTable 1 }

    Pf5000lldpRemEntry ::=
        SEQUENCE {
            pf5000lldpRemLocalPortNum       INTEGER,
            pf5000lldpRemIndex              INTEGER,
            pf5000lldpRemRemoteChassisType  INTEGER,
            pf5000lldpRemRemoteChassis      OCTET STRING,
            pf5000lldpRemRemotePortType     INTEGER,
            pf5000lldpRemRemotePort         OCTET STRING,
            pf5000lldpRemPortDesc           OCTET STRING,
            pf5000lldpRemSysName            OCTET STRING,
            pf5000lldpRemSysDesc            OCTET STRING
        }

pf5000lldpRemLocalPortNum OBJECT-TYPE
    SYNTAX  INTEGER
    ACCESS  read-only
    STATUS  mandatory
    DESCRIPTION
        "The discernment index of the port of this equipment which received the information about contiguity equipment"
    ::= {pf5000lldpRemEntry 2 }

pf5000lldpRemIndex OBJECT-TYPE
    SYNTAX  INTEGER
    ACCESS  read-only
    STATUS  mandatory
    DESCRIPTION
        "The index about contiguity equipment"
    ::= {pf5000lldpRemEntry 3 }

pf5000lldpRemRemoteChassisType OBJECT-TYPE
    SYNTAX  INTEGER {
        entPhysicalAlias(1),
        ifAlias(2),
        portEntPhysicalAlias(3),
        backplaneEntPhysicalAlias(4),
        macAddress(5),
        networkAddress(6)
    }
    ACCESS  read-only
    STATUS  mandatory
    DESCRIPTION
        "The chassis type about contiguity equipment"
    ::= {pf5000lldpRemEntry 4 }

pf5000lldpRemRemoteChassis OBJECT-TYPE
    SYNTAX  OCTET STRING
    ACCESS  read-only
    STATUS  mandatory
    DESCRIPTION
        "The chassis ID about contiguity equipment"
    ::= {pf5000lldpRemEntry 5 }

pf5000lldpRemRemotePortType OBJECT-TYPE
    SYNTAX  INTEGER {
        ifAlias(1),
        portEntPhysicalAlias(2),
        backplaneEntPhysicalAlias(3),
        macAddress(4),
        networkAddress(5),
        local(6)
    }
    ACCESS  read-only
    STATUS  mandatory
    DESCRIPTION
        "The port type about the port concerned of contiguity equipment"
    ::= {pf5000lldpRemEntry 6 }

pf5000lldpRemRemotePort OBJECT-TYPE
    SYNTAX  OCTET STRING
    ACCESS  read-only
    STATUS  mandatory
    DESCRIPTION
        "The port ID about the port concerned of contiguity equipment"
    ::= {pf5000lldpRemEntry 7 }

pf5000lldpRemPortDesc OBJECT-TYPE
    SYNTAX  OCTET STRING
    ACCESS  read-only
    STATUS  mandatory
    DESCRIPTION
        "Information about the port concerned of contiguity equipment"
    ::= {pf5000lldpRemEntry 8 }

pf5000lldpRemSysName OBJECT-TYPE
    SYNTAX  OCTET STRING
    ACCESS  read-only
    STATUS  mandatory
    DESCRIPTION
        "The system name about contiguity equipment"
    ::= {pf5000lldpRemEntry 9 }

pf5000lldpRemSysDesc OBJECT-TYPE
    SYNTAX  OCTET STRING
    ACCESS  read-only
    STATUS  mandatory
    DESCRIPTION
        "System information about contiguity equipment"
    ::= {pf5000lldpRemEntry 10 }

pf5000lldpRemOriginInfoTable OBJECT-TYPE
    SYNTAX  SEQUENCE OF Pf5000lldpRemOriginInfoEntry
    ACCESS  not-accessible
    STATUS  mandatory
    DESCRIPTION
        "The table about original with AlaxalA networks TLV of contiguity equipment"
    ::= { pf5000lldpRemoteOriginInfoData 1 }

pf5000lldpRemOriginInfoEntry OBJECT-TYPE
    SYNTAX  Pf5000lldpRemOriginInfoEntry
    ACCESS  not-accessible
    STATUS  mandatory
    DESCRIPTION
        "The entry about original with AlaxalA networks TLV of contiguity equipment"
    INDEX { pf5000lldpRemOriginInfoPortNum,pf5000lldpRemOriginInfoIndex }
    ::= { pf5000lldpRemOriginInfoTable 1 }

    Pf5000lldpRemOriginInfoEntry ::=
        SEQUENCE {
            pf5000lldpRemOriginInfoPortNum         INTEGER,
            pf5000lldpRemOriginInfoIndex           INTEGER,
            pf5000lldpRemOriginInfoLowerVlanList   OCTET STRING,
            pf5000lldpRemOriginInfoHigherVlanList  OCTET STRING,
            pf5000lldpRemOriginInfoIPv4Address     OCTET STRING,
            pf5000lldpRemOriginInfoIPv4PortType    INTEGER,
            pf5000lldpRemOriginInfoIPv4VlanId      INTEGER,
            pf5000lldpRemOriginInfoIPv6Address     OCTET STRING,
            pf5000lldpRemOriginInfoIPv6PortType    INTEGER,
            pf5000lldpRemOriginInfoIPv6VlanId      INTEGER
        }

pf5000lldpRemOriginInfoPortNum OBJECT-TYPE
    SYNTAX  INTEGER
    ACCESS  not-accessible
    STATUS  mandatory
    DESCRIPTION
        "The discernment index of the port of this equipment which received the information about contiguity equipment."
    ::= {pf5000lldpRemOriginInfoEntry 1 }

pf5000lldpRemOriginInfoIndex OBJECT-TYPE
    SYNTAX  INTEGER
    ACCESS  not-accessible
    STATUS  mandatory
    DESCRIPTION
        "The index about contiguity equipment"
    ::= {pf5000lldpRemOriginInfoEntry 2 }

pf5000lldpRemOriginInfoLowerVlanList OBJECT-TYPE
    SYNTAX  OCTET STRING
    ACCESS  read-only
    STATUS  mandatory
    DESCRIPTION
        "What expressed effective VLAN ID by the bit map by VLAN 1-2047 in the port concerned of contiguity equipment"
    ::= {pf5000lldpRemOriginInfoEntry 3 }

pf5000lldpRemOriginInfoHigherVlanList OBJECT-TYPE
    SYNTAX  OCTET STRING
    ACCESS  read-only
    STATUS  mandatory
    DESCRIPTION
        "What expressed effective VLAN ID by the bit map by VLAN 2048-4095 in the port concerned of contiguity equipment"
    ::= {pf5000lldpRemOriginInfoEntry 4 }

pf5000lldpRemOriginInfoIPv4Address OBJECT-TYPE
    SYNTAX  OCTET STRING
    ACCESS  read-only
    STATUS  mandatory
    DESCRIPTION
        "IPv4 address given to the port concerned of contiguity equipment"
    ::= {pf5000lldpRemOriginInfoEntry 5 }

pf5000lldpRemOriginInfoIPv4PortType OBJECT-TYPE
    SYNTAX  INTEGER
    ACCESS  read-only
    STATUS  mandatory
    DESCRIPTION
        "Port classification of the port of contiguity equipment concerned"
    ::= {pf5000lldpRemOriginInfoEntry 6 }

pf5000lldpRemOriginInfoIPv4VlanId OBJECT-TYPE
    SYNTAX  INTEGER
    ACCESS  read-only
    STATUS  mandatory
    DESCRIPTION
        "The smallest thing among VLAN ID to which IPv4 address is given"
    ::= {pf5000lldpRemOriginInfoEntry 7 }

pf5000lldpRemOriginInfoIPv6Address OBJECT-TYPE
    SYNTAX  OCTET STRING
    ACCESS  read-only
    STATUS  mandatory
    DESCRIPTION
        "The IPv6 address given to the port concerned of contiguity equipment"
    ::= {pf5000lldpRemOriginInfoEntry 8 }

pf5000lldpRemOriginInfoIPv6PortType OBJECT-TYPE
    SYNTAX  INTEGER
    ACCESS  read-only
    STATUS  mandatory
    DESCRIPTION
        "Port classification of the port of contiguity equipment concerned"
    ::= {pf5000lldpRemOriginInfoEntry 9 }

pf5000lldpRemOriginInfoIPv6VlanId OBJECT-TYPE
    SYNTAX  INTEGER
    ACCESS  read-only
    STATUS  mandatory
    DESCRIPTION
        "The smallest thing among VLAN ID to which the IPv6 address is given"
    ::= {pf5000lldpRemOriginInfoEntry 10 }

-- pf5200Switch group

pf5200ModelType OBJECT-TYPE
    SYNTAX  INTEGER {
        other(1),
        model-PF5240F-48T4XW(1500),
        model-PF5240R-48T4XW(1501)
    }
    ACCESS  read-only
    STATUS  mandatory
    DESCRIPTION
        "Model type of this system."
    ::= { pf5200Switch 1 }

--pf5200Software OBJECT-TYPE
--    SYNTAX  INTEGER
--    ACCESS  not-accessible
--    STATUS  mandatory
--    DESCRIPTION
--        "Software information of this system."
--    ::= { pf5200Switch 2 }

pf5200SoftwareName OBJECT-TYPE
    SYNTAX  DisplayString (SIZE (0..16))
    ACCESS  read-only
    STATUS  mandatory
    DESCRIPTION
        "Software name of this system."
    ::= { pf5200Software 1 }

pf5200SoftwareAbbreviation OBJECT-TYPE
    SYNTAX  DisplayString (SIZE (0..16))
    ACCESS  read-only
    STATUS  mandatory
    DESCRIPTION
        "System software abbreviation."
    ::= { pf5200Software 2 }

pf5200SoftwareVersion OBJECT-TYPE
    SYNTAX  DisplayString (SIZE (0..16))
    ACCESS  read-only
    STATUS  mandatory
    DESCRIPTION
        "System software version."
    ::= { pf5200Software 3 }

--pf5200SystemMsg OBJECT-TYPE
--    SYNTAX  INTEGER
--    ACCESS  not-accessible
--    STATUS  mandatory
--    DESCRIPTION
--        "System messege group."
--    ::= { pf5200Switch 3 }

pf5200SystemMsgText OBJECT-TYPE
    SYNTAX  DisplayString (SIZE (0..256))
    ACCESS  read-only
    STATUS  mandatory
    DESCRIPTION
        "The text of the system log message.For information about this code,
        see:  Operator's Manual. "
    ::= { pf5200SystemMsg 1 }

pf5200SystemMsgType OBJECT-TYPE
    SYNTAX  OCTET STRING (SIZE (1))
    ACCESS  read-only
    STATUS  mandatory
    DESCRIPTION
        "The event type. For information about this code, see:  Operator's Manual."
    ::= { pf5200SystemMsg 2 }

pf5200SystemMsgTimeStamp OBJECT-TYPE
    SYNTAX  DisplayString (SIZE (0..14))
    ACCESS  read-only
    STATUS  mandatory
    DESCRIPTION
        "The time that event occured. And that is expressed as type of
        MM/DD hh:mm:ss
            MM:month(01-12)
            DD:day(01-31)
            hh:hour(00-23)
            mm:minute(00-59)
            ss:second(00-59)
        Insert space between DD and hh."
    ::= { pf5200SystemMsg 3 }

pf5200SystemMsgLevel OBJECT-TYPE
    SYNTAX  OCTET STRING (SIZE (1))
    ACCESS  read-only
    STATUS  mandatory
    DESCRIPTION
        "The newest system message log level.For information about this code,
        see:  Operator's Manual. "
    ::= { pf5200SystemMsg 4 }

pf5200SystemMsgEventPoint OBJECT-TYPE
    SYNTAX  DisplayString (SIZE (0..8))
    ACCESS  read-only
    STATUS  mandatory
    DESCRIPTION
        "The code of part that system message error occured. For information
        about this code,see:  Operator's Manual. "
    ::= { pf5200SystemMsg 5 }

pf5200SystemMsgEventInterfaceID OBJECT-TYPE
    SYNTAX  DisplayString (SIZE (0..40))
    ACCESS  read-only
    STATUS  mandatory
    DESCRIPTION
        "Interface identification of system messages. For information
        about this code,see:  Operator's Manual."
    ::= { pf5200SystemMsg 6 }

pf5200SystemMsgEventCode OBJECT-TYPE
    SYNTAX  OCTET STRING (SIZE (4))
    ACCESS  read-only
    STATUS  mandatory
    DESCRIPTION
        "Event kind code of system messages. For information about this code,
        see:  Operator's Manual. "
    ::= { pf5200SystemMsg 7 }

pf5200SystemMsgAdditionalCode OBJECT-TYPE
    SYNTAX  OCTET STRING (SIZE (6))
    ACCESS  read-only
    STATUS  mandatory
    DESCRIPTION
        "Additional code of system messages. For information about this code,
        see:  Operator's Manual. "
    ::= { pf5200SystemMsg 8 }

--pf5200SnmpAgent OBJECT-TYPE
--    SYNTAX  INTEGER
--    ACCESS  not-accessible
--    STATUS  mandatory
--    DESCRIPTION
--        "Related information of SNMP agent."
--    ::= { pf5200Switch 4 }

pf5200SnmpSendReceiveSize OBJECT-TYPE
    SYNTAX  INTEGER
    ACCESS  read-only
    STATUS  mandatory
    DESCRIPTION
        "SNMP packet data size in Manager-to-Agent communication. The value is
        displayed in bytes."
    ::= { pf5200SnmpAgent 1 }

pf5200SnmpReceiveDelay OBJECT-TYPE
    SYNTAX  INTEGER
    ACCESS  read-only
    STATUS  mandatory
    DESCRIPTION
        "A recommendable interval to receive packets from Manager.The value is
        displayed in milliseconds."
    ::= { pf5200SnmpAgent 2 }

pf5200SnmpContinuousSend OBJECT-TYPE
    SYNTAX  INTEGER
    ACCESS  read-only
    STATUS  mandatory
    DESCRIPTION
        "Number of times that is recommendable continuous transmission
        packets."
    ::= { pf5200SnmpAgent 3 }

pf5200SnmpObjectMaxNumber OBJECT-TYPE
    SYNTAX  INTEGER
    ACCESS  read-only
    STATUS  mandatory
    DESCRIPTION
        "Max number of objects that contain SNMP packet."
    ::= { pf5200SnmpAgent 4 }

--pf5200SerialNumber OBJECT-TYPE
--    SYNTAX  DisplayString (SIZE (0..30))
--    ACCESS  read-only
--    STATUS  mandatory
--    DESCRIPTION
--        "Management information (SerialNumber) of RMP2-CARD."
--    ::= { pf5200Switch 5 }

pf5200LicenseNumber OBJECT-TYPE
    SYNTAX  INTEGER
    ACCESS  read-only
    STATUS  mandatory
    DESCRIPTION
        "The number of the configured license serial numbers."
    ::= { pf5200License 1 }

pf5200LicenseTable OBJECT-TYPE
    SYNTAX  SEQUENCE OF Pf5200LicenseTableEntry
    ACCESS  not-accessible
    STATUS  mandatory
    DESCRIPTION
        "The table containing the license information."
    ::= { pf5200License 2 }

pf5200LicenseEntry OBJECT-TYPE
    SYNTAX  Pf5200LicenseTableEntry
    ACCESS  not-accessible
    STATUS  mandatory
    DESCRIPTION
        "The entry of license information."
    INDEX { pf5200LicenseIndex }
    ::= { pf5200LicenseTable 1 }

    Pf5200LicenseTableEntry ::=
        SEQUENCE {
            pf5200LicenseIndex
                INTEGER,
            pf5200LicenseSerialNumber
                DisplayString,
            pf5200LicenseOptionNumber
                INTEGER
        }

pf5200LicenseIndex OBJECT-TYPE
    SYNTAX  INTEGER
    ACCESS  not-accessible
    STATUS  mandatory
    DESCRIPTION
        "The unique index number given for each serial number. The number is from 1 to pf5200LicenseNumber."
    ::= { pf5200LicenseEntry 1 }

pf5200LicenseSerialNumber OBJECT-TYPE
    SYNTAX  DisplayString
    ACCESS  read-only
    STATUS  mandatory
    DESCRIPTION
        "The serial number."
    ::= { pf5200LicenseEntry 2 }

pf5200LicenseOptionNumber OBJECT-TYPE
    SYNTAX  INTEGER
    ACCESS  read-only
    STATUS  mandatory
    DESCRIPTION
        "The number of option licenses associated with the serial number."
    ::= { pf5200LicenseEntry 3 }

pf5200LicenseOptionTable OBJECT-TYPE
    SYNTAX  SEQUENCE OF Pf5200LicenseOptionTableEntry
    ACCESS  not-accessible
    STATUS  mandatory
    DESCRIPTION
        "The table containing option licenses information associated with the serial number."
    ::= { pf5200License 3 }

pf5200LicenseOptionEntry OBJECT-TYPE
    SYNTAX  Pf5200LicenseOptionTableEntry
    ACCESS  not-accessible
    STATUS  mandatory
    DESCRIPTION
        "The entry of the option license information associated with the serial number."
    INDEX { pf5200LicenseOptionIndex,pf5200LicenseOptionNumberIndex }
    ::= { pf5200LicenseOptionTable 1 }

    Pf5200LicenseOptionTableEntry ::=
        SEQUENCE {
            pf5200LicenseOptionIndex
                INTEGER,
            pf5200LicenseOptionNumberIndex
                INTEGER,
            pf5200LicenseOptionSoftwareName
                DisplayString,
            pf5200LicenseOptionSoftwareAbbreviation
                DisplayString
        }

pf5200LicenseOptionIndex OBJECT-TYPE
    SYNTAX  INTEGER
    ACCESS  not-accessible
    STATUS  mandatory
    DESCRIPTION
        "The unique index number given for each serial number. The same number as pf5200LicenseIndex."
    ::= { pf5200LicenseOptionEntry 1 }

pf5200LicenseOptionNumberIndex OBJECT-TYPE
    SYNTAX  INTEGER
    ACCESS  not-accessible
    STATUS  mandatory
    DESCRIPTION
        "The unique index number of option licenses information which is given for each serial number. The number is from 1 to pf5200LicenseNumber."
    ::= { pf5200LicenseOptionEntry 2 }

pf5200LicenseOptionSoftwareName OBJECT-TYPE
    SYNTAX  DisplayString 
    ACCESS  read-only
    STATUS  mandatory
    DESCRIPTION
        "The software model name of the option license information associated with the serial number."
    ::= { pf5200LicenseOptionEntry 3 }

pf5200LicenseOptionSoftwareAbbreviation OBJECT-TYPE
    SYNTAX  DisplayString 
    ACCESS  read-only
    STATUS  mandatory
    DESCRIPTION
        "The software abbreviated name of the option license information associated with the serial number. "
    ::= { pf5200LicenseOptionEntry 4 }

-- pf5200Device group

pf5200ChassisMaxNumber OBJECT-TYPE
    SYNTAX  INTEGER
    ACCESS  read-only
    STATUS  mandatory
    DESCRIPTION
        "Max number of cluster chassis that can connect to this router."
    ::= { pf5200Chassis 1 }


pf5200ChassisTable OBJECT-TYPE
    SYNTAX  SEQUENCE OF Pf5200ChassisTableEntry
    ACCESS  not-accessible
    STATUS  mandatory
    DESCRIPTION
        "A table containing chassis information."
    ::= { pf5200Chassis 2 }

pf5200ChassisEntry OBJECT-TYPE
    SYNTAX  Pf5200ChassisTableEntry
    ACCESS  not-accessible
    STATUS  mandatory
    DESCRIPTION
        "An entry containing specific chassis."
    INDEX { pf5200ChassisIndex }
    ::= { pf5200ChassisTable 1 }

    Pf5200ChassisTableEntry ::=
        SEQUENCE {
            pf5200ChassisIndex
                INTEGER,
            pf5200ChassisType
                INTEGER,
            pf5200ChassisStatus
                INTEGER,
            pf5200StsLedStatus1
                INTEGER,
            pf5200StsLedStatus2
                INTEGER,
            pf5200MgmtPortStatus
                INTEGER,
            pf5200CpuName
                DisplayString,
            pf5200CpuClock
                INTEGER,
            pf5200Cpu2Name
                DisplayString,
            pf5200MemoryTotalSize
                INTEGER,
            pf5200MemoryUsedSize
                INTEGER,
            pf5200MemoryFreeSize
                INTEGER,
            pf5200Memory2TotalSize
                INTEGER,
            pf5200RomVersion
                DisplayString,
            pf5200CpuLoad1m
                INTEGER,
            pf5200FlashTotalSize
                INTEGER,
            pf5200FlashUsedSize
                INTEGER,
            pf5200FlashFreeSize
                INTEGER,
            pf5200SdCardStatus
                INTEGER,
            pf5200SdCardTotalSize
                INTEGER,
            pf5200SdCardUsedSize
                INTEGER,
            pf5200SdCardFreeSize
                INTEGER,
            pf5200PhysLineNumber
                INTEGER,
            pf5200TemperatureStatusNumber
                INTEGER,
            pf5200PowerUnitNumber
                INTEGER,
            pf5200FanNumber
                INTEGER,
            pf5200Fandirection
                INTEGER,
            pf5200TotalAccumRunTime
                INTEGER,
            pf5200CriticalAccumRunTime
                INTEGER,
            pf5200SystemWattage
                Gauge,
            pf5200SystemWattageTime
                DisplayString
        }

pf5200ChassisIndex OBJECT-TYPE
    SYNTAX  INTEGER
    ACCESS  not-accessible
    STATUS  mandatory
    DESCRIPTION
        "A number to specify pf5200ChassisEntry."
    ::= { pf5200ChassisEntry 1 }

pf5200ChassisType OBJECT-TYPE
    SYNTAX  INTEGER {
        other(1),
        model-PF5240F-48T4XW(1500),
        model-PF5240R-48T4XW(1501)
    }
    ACCESS  read-only
    STATUS  mandatory
    DESCRIPTION
        "Chassis type of this system."
    ::= { pf5200ChassisEntry 2 }

pf5200ChassisStatus OBJECT-TYPE
    SYNTAX  INTEGER {
        up(2)
    }
    ACCESS  read-only
    STATUS  mandatory
    DESCRIPTION
        "Current status of this chassis."
    ::= { pf5200ChassisEntry 3 }

pf5200StsLedStatus1 OBJECT-TYPE
    SYNTAX  INTEGER {
        green-light-blink(1),
        green-light-on(2),
        red-light-blink(3),
        red-light-on(4),
        light-off(6)
    }
    ACCESS  read-only
    STATUS  mandatory
    DESCRIPTION
        "The state of STATUS1 LED of the device is shown."
    ::= { pf5200ChassisEntry 4 }

pf5200StsLedStatus2 OBJECT-TYPE
    SYNTAX  INTEGER {
        blue-light-on(5),
        light-off(6),
        blue-light-blink(7)
    }
    ACCESS  read-only
    STATUS  mandatory
    DESCRIPTION
        "The state of STATUS2 LED of the device is shown."
    ::= { pf5200ChassisEntry 5 }

pf5200MgmtPortStatus OBJECT-TYPE
    SYNTAX  INTEGER {
        ok(2),
        fault(4),
        disconnected(6),
        test(9),
        nothing-configuration(10)
    }
    ACCESS  read-only
    STATUS  mandatory
    DESCRIPTION
        "The state of management-port status of the device."
    ::= { pf5200ChassisEntry 6 }

pf5200CpuName OBJECT-TYPE
    SYNTAX  DisplayString
    ACCESS  read-only
    STATUS  mandatory
    DESCRIPTION
        "CPU name is shown by the character string of 16 characters or less." 
    ::= { pf5200ChassisEntry 7 }

pf5200CpuClock OBJECT-TYPE
    SYNTAX  INTEGER
    ACCESS  read-only
    STATUS  mandatory
    DESCRIPTION
        "CPU clock is shown by the numerical value."
    ::= { pf5200ChassisEntry 8 }

pf5200Cpu2Name OBJECT-TYPE
    SYNTAX  DisplayString
    ACCESS  read-only
    STATUS  mandatory
    DESCRIPTION
        "CPU2 name is shown by the character string of 16 characters or less."
    ::= { pf5200ChassisEntry 9 }

pf5200MemoryTotalSize OBJECT-TYPE
    SYNTAX  INTEGER
    ACCESS  read-only
    STATUS  mandatory
    DESCRIPTION
        "The installing memory size is shown by the numerical value. "
    ::= { pf5200ChassisEntry 10 }

pf5200MemoryUsedSize OBJECT-TYPE
    SYNTAX  INTEGER
    ACCESS  read-only
    STATUS  mandatory
    DESCRIPTION
        "The use memory size is shown by the numerical value."
    ::= { pf5200ChassisEntry 11 }

pf5200MemoryFreeSize OBJECT-TYPE
    SYNTAX  INTEGER
    ACCESS  read-only
    STATUS  mandatory
    DESCRIPTION
        "The unused memory size is shown by the numerical value."
    ::= { pf5200ChassisEntry 12 }

pf5200Memory2TotalSize OBJECT-TYPE
    SYNTAX  INTEGER
    ACCESS  read-only
    STATUS  mandatory
    DESCRIPTION
        "The installing memory2 size is shown by the numerical value. "
    ::= { pf5200ChassisEntry 13 }

pf5200RomVersion OBJECT-TYPE
    SYNTAX  DisplayString
    ACCESS  read-only
    STATUS  mandatory
    DESCRIPTION
        "The version of ROM equipped with BCU is shown by the character string."
    ::= { pf5200ChassisEntry 14 }

pf5200CpuLoad1m OBJECT-TYPE
    SYNTAX  INTEGER
    ACCESS  read-only
    STATUS  mandatory
    DESCRIPTION
        "CPU utilization of one minute is shown by the numerical value."
    ::= { pf5200ChassisEntry 15 }

pf5200FlashTotalSize OBJECT-TYPE
    SYNTAX  INTEGER
    ACCESS  read-only
    STATUS  mandatory
    DESCRIPTION
        "The total of filesystem use capacity and unused capacity in a built-in memory 
        is shown."
    ::= { pf5200ChassisEntry 16 }

pf5200FlashUsedSize OBJECT-TYPE
    SYNTAX  INTEGER
    ACCESS  read-only
    STATUS  mandatory
    DESCRIPTION
        "The use capacity of the filesystem in a built-in memory is shown."
    ::= { pf5200ChassisEntry 17 }

pf5200FlashFreeSize OBJECT-TYPE
    SYNTAX  INTEGER
    ACCESS  read-only
    STATUS  mandatory
    DESCRIPTION
        "The unused capacity of the filesystem in a built-in memory is shown. "
    ::= { pf5200ChassisEntry 18 }

pf5200SdCardStatus OBJECT-TYPE
    SYNTAX  INTEGER {
        connected(2),
        disconnected(32)
    }
    ACCESS  read-only
    STATUS  mandatory
    DESCRIPTION
        "The SD card connection is shown."
    ::= { pf5200ChassisEntry 19 }

pf5200SdCardTotalSize OBJECT-TYPE
    SYNTAX  INTEGER
    ACCESS  read-only
    STATUS  mandatory
    DESCRIPTION
        "Total capacity of the SD card is shown by the numerical value. It responds by -1 
        at the MC card unconnection."
    ::= { pf5200ChassisEntry 20 }

pf5200SdCardUsedSize OBJECT-TYPE
    SYNTAX  INTEGER
    ACCESS  read-only
    STATUS  mandatory
    DESCRIPTION
        "The use capacity of the SD card is shown by the numerical value. It responds by -1 
        at the SD card unconnection. "
    ::= { pf5200ChassisEntry 21 }

pf5200SdCardFreeSize OBJECT-TYPE
    SYNTAX  INTEGER
    ACCESS  read-only
    STATUS  mandatory
    DESCRIPTION
        "The remainder capacity of the SD card is shown by the numerical value. It
        responds by -1 at the SD card unconnection."
    ::= { pf5200ChassisEntry 22 }

pf5200PhysLineNumber OBJECT-TYPE
    SYNTAX  INTEGER
    ACCESS  read-only
    STATUS  mandatory
    DESCRIPTION
        "Number of physical lines."
    ::= { pf5200ChassisEntry 23 }

pf5200TemperatureStatusNumber OBJECT-TYPE
    SYNTAX  INTEGER
    ACCESS  read-only
    STATUS  mandatory
    DESCRIPTION
        "The maximum number of pf5200TemperatureStatus in this chassis."
    ::= { pf5200ChassisEntry 24 }

pf5200PowerUnitNumber OBJECT-TYPE
    SYNTAX  INTEGER
    ACCESS  read-only
    STATUS  mandatory
    DESCRIPTION
        "Number of maximum power switches that this router can connect its."
    ::= { pf5200ChassisEntry 25 }

pf5200FanNumber OBJECT-TYPE
    SYNTAX  INTEGER
    ACCESS  read-only
    STATUS  mandatory
    DESCRIPTION
        "The maximum number of fans that can connect to this chassis."
    ::= { pf5200ChassisEntry 26 }

pf5200Fandirection OBJECT-TYPE
    SYNTAX  INTEGER {
        front-to-rear(0),
        rear-to-front(1)
    }
    ACCESS  read-only
    STATUS  mandatory
    DESCRIPTION
        "The direction of fan of system is shown."
    ::= { pf5200ChassisEntry 27 }

pf5200TotalAccumRunTime OBJECT-TYPE
    SYNTAX  INTEGER
    ACCESS  read-only
    STATUS  mandatory
    DESCRIPTION
        "Total operation time after operation of device begins."
    ::= { pf5200ChassisEntry 28 }

pf5200CriticalAccumRunTime OBJECT-TYPE
    SYNTAX  INTEGER
    ACCESS  read-only
    STATUS  mandatory
    DESCRIPTION
        "Operating time under environment of 45 degrees C or more."
    ::= { pf5200ChassisEntry 29 }

pf5200SystemWattage OBJECT-TYPE
    SYNTAX  Gauge
    ACCESS  read-only
    STATUS  mandatory
    DESCRIPTION
        "The power consumption of system."
    ::= { pf5200ChassisEntry 30 }

pf5200SystemWattageTime OBJECT-TYPE
    SYNTAX  DisplayString
    ACCESS  read-only
    STATUS  mandatory
    DESCRIPTION
        "The time that event occured. And that is expressed as type of
        MM/DD hh:mm:ss
            MM:month(01-12)
            DD:day(01-31)
            hh:hour(00-23)
            mm:minute(00-59)
            ss:second(00-59)
        Insert space between DD and hh."
    ::= { pf5200ChassisEntry 31 }

pf5200TemperatureStatusTable OBJECT-TYPE
    SYNTAX  SEQUENCE OF Pf5200TemperatureStatusEntry
    ACCESS  not-accessible
    STATUS  mandatory
    DESCRIPTION
        "The table of ambient temperature status maintained by the
        environmental monitor."
    ::= { pf5200Chassis 3 }

pf5200TemperatureStatusEntry OBJECT-TYPE
    SYNTAX  Pf5200TemperatureStatusEntry
    ACCESS  not-accessible
    STATUS  mandatory
    DESCRIPTION
        "An entry in the ambient temperature status table, representing
        the status of the associated testpoint maintained by the
        environmental monitor."
    INDEX { pf5200ChassisIndex, pf5200TemperatureStatusIndex }
    ::= { pf5200TemperatureStatusTable 1 }

    Pf5200TemperatureStatusEntry ::=
        SEQUENCE {
            pf5200TemperatureStatusIndex
                INTEGER,
            pf5200TemperatureStatusDescr
                DisplayString,
            pf5200TemperatureStatusValue
                Integer32,
            pf5200TemperatureThreshold
                Integer32,
            pf5200TemperatureState
                INTEGER
        }

pf5200TemperatureStatusIndex OBJECT-TYPE
    SYNTAX  INTEGER
    ACCESS  not-accessible
    STATUS  mandatory
    DESCRIPTION
        "Unique index for the testpoint being instrumented.
        This index is for SNMP purposes only, and has no
        intrinsic meaning."
    ::= { pf5200TemperatureStatusEntry 1 }

pf5200TemperatureStatusDescr OBJECT-TYPE
    SYNTAX  DisplayString(SIZE(0..32))
    ACCESS  read-only
    STATUS  mandatory
    DESCRIPTION
        "Textual description of the testpoint being instrumented.
        This description is a short textual label, suitable as a
        human-sensible identification for the rest of the
        information in the entry."
    ::= { pf5200TemperatureStatusEntry 2 }

pf5200TemperatureStatusValue OBJECT-TYPE
    SYNTAX  Integer32
    ACCESS  read-only
    STATUS  mandatory
    DESCRIPTION
        "The current measurement of the testpoint being instrumented."
    ::= { pf5200TemperatureStatusEntry 3 }

pf5200TemperatureThreshold OBJECT-TYPE
    SYNTAX  Integer32
    ACCESS  read-only
    STATUS  mandatory
    DESCRIPTION
        "The highest value that the associated instance of the
        object pf5200TemperatureStatusValue may obtain
        before an emergency shutdown of the managed device is
        initiated."
    ::= { pf5200TemperatureStatusEntry 4 }

pf5200TemperatureState OBJECT-TYPE
    SYNTAX  INTEGER {
        normal(1),
        caution(2),
        warning(3),
        fatal(4)
    }
    ACCESS  read-only
    STATUS  mandatory
    DESCRIPTION
        "The current state of the testpoint being instrumented."
        ::= { pf5200TemperatureStatusEntry 5 }

pf5200PowerUnitTable OBJECT-TYPE
    SYNTAX  SEQUENCE OF Pf5200PowerUnitTableEntry
    ACCESS  not-accessible
    STATUS  mandatory
    DESCRIPTION
        "A table containing power unit information."
    ::= { pf5200Chassis 4 }

pf5200PowerUnitEntry OBJECT-TYPE
    SYNTAX  Pf5200PowerUnitTableEntry
    ACCESS  not-accessible
    STATUS  mandatory
    DESCRIPTION
        "An entry containing power unit information."
    INDEX { pf5200ChassisIndex, pf5200PowerUnitIndex }
    ::= { pf5200PowerUnitTable 1 }

    Pf5200PowerUnitTableEntry ::=
        SEQUENCE {
            pf5200PowerUnitIndex
                INTEGER,
            pf5200PowerConnectStatus
                INTEGER,
            pf5200PowerSupplyStatus
                INTEGER,
            pf5200ModuleSlotType
                INTEGER,
            pf5200PowerFanDirection
                INTEGER
        }

pf5200PowerUnitIndex OBJECT-TYPE
    SYNTAX  INTEGER
    ACCESS  not-accessible
    STATUS  mandatory
    DESCRIPTION
        "A number to position of the power units.The value from 1
        to pf5200PowerUnitNumber."
    ::= { pf5200PowerUnitEntry 1 }
        
pf5200PowerConnectStatus OBJECT-TYPE
    SYNTAX  INTEGER {
        connected(2),
        disconnected(32)
    }
    ACCESS  read-only
    STATUS  mandatory
    DESCRIPTION
        "The current connection status of the power unit."
    ::= { pf5200PowerUnitEntry 2 }

pf5200PowerSupplyStatus OBJECT-TYPE
    SYNTAX  INTEGER {
        ok(2),
        fault(4),
        disconnected(-1)
    }
    ACCESS  read-only
    STATUS  mandatory
    DESCRIPTION
        "Status of power supply."
    ::= { pf5200PowerUnitEntry 3 }

pf5200ModuleSlotType OBJECT-TYPE
    SYNTAX  INTEGER {
        ac(1),
        disconnected(-1)
    }
    ACCESS  read-only
    STATUS  mandatory
    DESCRIPTION
        "The type of module slot is shown."
    ::= { pf5200PowerUnitEntry 4 }

pf5200PowerFanDirection OBJECT-TYPE
    SYNTAX  INTEGER {
        front-to-rear(0),
        rear-to-front(1)
    }
    ACCESS  read-only
    STATUS  mandatory
    DESCRIPTION
        "The direction of fan of power supply is shown."
    ::= { pf5200PowerUnitEntry 5 }

pf5200FanTable OBJECT-TYPE
    SYNTAX  SEQUENCE OF Pf5200FanTableEntry
    ACCESS  not-accessible
    STATUS  mandatory
    DESCRIPTION
        "A table containing fan information."
    ::= { pf5200Chassis 5 }

pf5200FanEntry OBJECT-TYPE
    SYNTAX  Pf5200FanTableEntry
    ACCESS  not-accessible
    STATUS  mandatory
    DESCRIPTION
        "This entry containing information for a fan."
    INDEX { pf5200ChassisIndex, pf5200FanIndex }
    ::= { pf5200FanTable 1 }

    Pf5200FanTableEntry ::=
        SEQUENCE {
            pf5200FanIndex
                INTEGER,
            pf5200FanStatus
                INTEGER,
            pf5200FanDirection
                INTEGER
        }

pf5200FanIndex OBJECT-TYPE
    SYNTAX  INTEGER
    ACCESS  not-accessible
    STATUS  mandatory
    DESCRIPTION
        "Index to indicate position of fans."
    ::= { pf5200FanEntry 1 }

pf5200FanStatus OBJECT-TYPE
    SYNTAX  INTEGER {
        ok(2),
        high-speed(3),
        fault(4),
        disconnected(32)
    }
    ACCESS  read-only
    STATUS  mandatory
    DESCRIPTION
        "Status of fans."
    ::= { pf5200FanEntry 2 }

pf5200FanDirection OBJECT-TYPE
    SYNTAX  INTEGER {
        front-to-rear(0),
        rear-to-front(1)
    }
    ACCESS  read-only
    STATUS  mandatory
    DESCRIPTION
        "The direction of main fan is shown."
    ::= { pf5200FanEntry 3 }

pf5200PhysLineTable OBJECT-TYPE
    SYNTAX  SEQUENCE OF Pf5200PhysLineTableEntry
    ACCESS  not-accessible
    STATUS  mandatory
    DESCRIPTION
        "A table containing physical port information."
    ::= { pf5200PhysLine 1 }

pf5200PhysLineEntry OBJECT-TYPE
    SYNTAX  Pf5200PhysLineTableEntry
    ACCESS  not-accessible
    STATUS  mandatory
    DESCRIPTION
        "An entry containing physical port."
    INDEX { pf5200ChassisIndex, pf5200PhysLineIndex }
    ::= { pf5200PhysLineTable 1 }

    Pf5200PhysLineTableEntry ::=
        SEQUENCE {
            pf5200PhysLineIndex
                INTEGER,
            pf5200PhysLineConnectorType
                INTEGER,
            pf5200PhysLineOperStatus
                INTEGER,
            pf5200PhysLineIfIndexNumber
                INTEGER,
            pf5200PhysLineTransceiverStatus
                INTEGER
        }

pf5200PhysLineIndex OBJECT-TYPE
    SYNTAX  INTEGER
    ACCESS  not-accessible
    STATUS  mandatory
    DESCRIPTION
        "Physical port number. The value is from 1 to pf5200NifLineNumber."
    ::= { pf5200PhysLineEntry 1 }

pf5200PhysLineConnectorType OBJECT-TYPE
    SYNTAX  INTEGER {
        other(1),
        type1000BASE-LX(301),
        type1000BASE-SX(302),
        type1000BASE-LH(303),
        type10GBASE-SR(401),
        type10GBASE-LR(402),
        type10GBASE-ER(403),
        type10GBASE-CU1M(405),
        type10GBASE-CU3M(406),
        type10GBASE-CU5M(407)
    }
    ACCESS  read-only
    STATUS  mandatory
    DESCRIPTION
        "Connector type is connected physical port. The value is 1(other)
        when connector is disconnected or connector type is unknown."
    ::= { pf5200PhysLineEntry 2 }

pf5200PhysLineOperStatus OBJECT-TYPE
    SYNTAX  INTEGER {
        other(1),
        active(2),
        initialization(3),
        down(4),
        lock(6),
        close(7),
        line-fault(8),
        test(9),
        nothing-configuration(10)
    }
    ACCESS  read-only
    STATUS  mandatory
    DESCRIPTION
        "Status of physical port. The value is -1 when PSU or NIF board is
        disconnected."
    ::= { pf5200PhysLineEntry 3 }

pf5200PhysLineIfIndexNumber OBJECT-TYPE
    SYNTAX  INTEGER
    ACCESS  read-only
    STATUS  mandatory
    DESCRIPTION
        "Number of ifIndex which is included in physical port.The value is -1
        when PSU board or NIF board is disconnected."
    ::= { pf5200PhysLineEntry 4 }

pf5200PhysLineTransceiverStatus OBJECT-TYPE
    SYNTAX  INTEGER {
        unchangeable-transceiver(1),
        sfp-mounted(20),
        sfp-unmounted(21),
        unsupported-sfp-mounted(22),
        sfp-status-unknown(23)
    }
    ACCESS  read-only
    STATUS  mandatory
    DESCRIPTION
        "Type and status of replaceable transceiver."
    ::= { pf5200PhysLineEntry 5 }
--
-- pf5200FdbClearMIB      OBJECT IDENTIFIER ::= { pf5200OperationCommand 1 }
--

pf5200FdbClearSet OBJECT-TYPE
    SYNTAX  INTEGER {
        initialValue(0),
        processing(1),
        failure(2),
        success(3)
    }
    ACCESS  read-write
    STATUS  mandatory
    DESCRIPTION
        "Fdb clear information. When want to clear fdb, 
        then set value of this MIB as 1."
    ::= { pf5200FdbClearMIB 1 }

pf5200FdbClearReqTime OBJECT-TYPE
    SYNTAX  TimeTicks
    ACCESS  read-only
    STATUS  mandatory
    DESCRIPTION
        "This object indicates the most recent time that
        received the demand to clear Fdb information.(sysUpTime)"
    ::= { pf5200FdbClearMIB 2 }

pf5200FdbClearSuccessTime OBJECT-TYPE
    SYNTAX  TimeTicks
    ACCESS  read-only
    STATUS  mandatory
    DESCRIPTION
        "This object indicates the time of the most recent
         Fdb clearing success.(sysUpTime)"
    ::= { pf5200FdbClearMIB 3 }

pf5200SystemManageReload OBJECT-TYPE
    SYNTAX  INTEGER {
        initialValue(0),
        restart(1),
        standby(2)
    }
    ACCESS  read-write
    STATUS  mandatory
    DESCRIPTION
        "System reload information. When want to restart or standby, 
        then set value of this MIB as 1 or 2."
    ::= { pf5200SystemManagementMIB 1 }

pf5000OspfVirtIfStateChange TRAP-TYPE
    ENTERPRISE  pf5000OspfTraps
    VARIABLES {
        pf5000OspfVirtIfDomainNumber,
        pf5000OspfRouterId,
        pf5000OspfVirtIfAreaId,
        pf5000OspfVirtIfNeighbor,
        pf5000OspfVirtIfState
    }
    DESCRIPTION
        "An pf5000OspfIfStateChange trap signifies that there has  been a change 
        in the state of an OSPF virtual interface."
    ::= 1

pf5000OspfNbrStateChange TRAP-TYPE
    ENTERPRISE  pf5000OspfTraps
    VARIABLES {
        pf5000OspfNbrDomainNumber,
        pf5000OspfRouterId,
        pf5000OspfNbrIpAddr,
        pf5000OspfNbrAddressLessIndex,
        pf5000OspfNbrRtrId,
        pf5000OspfNbrState
    }
    DESCRIPTION
        "An pf5000OspfNbrStateChange trap signifies that
        there  has been a change in the state of a non-
        virtual OSPF neighbor.   This  trap  should  be
        generated  when  the  neighbor  state regresses
        (e.g., goes from Attempt or Full  to  1-Way  or
        Down)  or progresses to a terminal state (e.g.,
        2-Way or Full).  When an  neighbor  transitions
        from  or  to Full on non-broadcast multi-access
        and broadcast networks, the trap should be gen-
        erated  by the designated router.  A designated
        router transitioning to Down will be  noted  by
        pf5000OspfIfStateChange."
    ::= 2

pf5000OspfVirtNbrStateChange TRAP-TYPE
    ENTERPRISE  pf5000OspfTraps
    VARIABLES {
        pf5000OspfVirtNbrDomainNumber,
        pf5000OspfRouterId,
        pf5000OspfVirtNbrArea,
        pf5000OspfVirtNbrRtrId,
        pf5000OspfVirtNbrState
    }
    DESCRIPTION
        "An pf5000OspfIfStateChange trap signifies that there
        has  been a change in the state of an OSPF vir-
        tual neighbor.  This trap should  be  generated
        when  the  neighbor state regresses (e.g., goes
        from Attempt or  Full  to  1-Way  or  Down)  or
        progresses to a terminal state (e.g., Full)."
    ::= 3

pf5000OspfIfConfigError TRAP-TYPE
    ENTERPRISE  pf5000OspfTraps
    VARIABLES {
        pf5000OspfIfDomainNumber,
        pf5000OspfRouterId,
        pf5000OspfIfIpAddress,
        pf5000OspfAddressLessIf,
        pf5000OspfPacketSrc,
        pf5000OspfConfigErrorType,
        pf5000OspfPacketType
    }
    DESCRIPTION
        "An pf5000OspfIfConfigError  trap  signifies  that  a
        packet  has  been received on a non-virtual in-
        terface  from  a  router  whose   configuration
        parameters  conflict  with this router's confi-
        guration parameters.  Note that the  event  op-
        tionMismatch  should  cause  a  trap only if it
        prevents an adjacency from forming."
    ::= 4

pf5000OspfVirtIfConfigError TRAP-TYPE
    ENTERPRISE  pf5000OspfTraps
    VARIABLES {
        pf5000OspfVirtIfDomainNumber,
        pf5000OspfRouterId,
        pf5000OspfVirtIfAreaId,
        pf5000OspfVirtIfNeighbor,
        pf5000OspfConfigErrorType,
        pf5000OspfPacketType
    }
    DESCRIPTION
        "An pf5000OspfConfigError trap signifies that a pack-
        et  has  been  received  on a virtual interface
        from a router  whose  configuration  parameters
        conflict   with   this  router's  configuration
        parameters.  Note that the event optionMismatch
        should  cause a trap only if it prevents an ad-
        jacency from forming."
    ::= 5

pf5000OspfIfAuthFailure TRAP-TYPE
    ENTERPRISE  pf5000OspfTraps
    VARIABLES {
        pf5000OspfIfDomainNumber,
        pf5000OspfRouterId,
        pf5000OspfIfIpAddress,
        pf5000OspfAddressLessIf,
        pf5000OspfPacketSrc,
        pf5000OspfConfigErrorType,
        pf5000OspfPacketType
    }
    DESCRIPTION
        "An pf5000OspfIfAuthFailure  trap  signifies  that  a
        packet  has  been received on a non-virtual in-
        terface from a router whose authentication  key
        or  authentication  type  conflicts  with  this
        router's authentication key  or  authentication
        type."
    ::= 6

pf5000OspfVirtIfAuthFailure TRAP-TYPE
    ENTERPRISE  pf5000OspfTraps
    VARIABLES {
        pf5000OspfVirtIfDomainNumber,
        pf5000OspfRouterId,
        pf5000OspfVirtIfAreaId,
        pf5000OspfVirtIfNeighbor,
        pf5000OspfConfigErrorType,
        pf5000OspfPacketType
    }
    DESCRIPTION
        "An pf5000OspfVirtIfAuthFailure trap signifies that a
        packet has been received on a virtual interface
        from a router whose authentication key  or  au-
        thentication  type conflicts with this router's
        authentication key or authentication type."
    ::= 7

pf5000OspfIfStateChange TRAP-TYPE
    ENTERPRISE  pf5000OspfTraps
    VARIABLES {
        pf5000OspfIfDomainNumber,
        pf5000OspfRouterId,
        pf5000OspfIfIpAddress,
        pf5000OspfAddressLessIf,
        pf5000OspfIfState
    }
    DESCRIPTION
        "An pf5000OspfIfStateChange trap signifies that there
        has been a change in the state of a non-virtual
        OSPF interface. This trap should  be  generated
        when  the interface state regresses (e.g., goes
        from Dr to Down) or progresses  to  a  terminal
        state  (i.e.,  Point-to-Point, DR Other, Dr, or
        Backup)."
    ::= 16 

pf5000OadpNeighborCachelastChangeTrap TRAP-TYPE
    ENTERPRISE  pf5000OadpMIBNotifications
    VARIABLES   { pf5000OadpNeighborCacheLastChange }
    DESCRIPTION
        "This trap indicates that information of OADP neighbor nodes is updated."
    ::= 1 

END

PF5000-PF5200-TRAP DEFINITIONS ::= BEGIN
IMPORTS
enterprises
    FROM RFC1155-SMI
TRAP-TYPE
    FROM RFC-1215
ifIndex
    FROM RFC1213-MIB
pf5200, pf5200TrapId,
pf5000AxrpGroupRingId, pf5000AxrpGroupMode, pf5000AxrpGroupRingAttribute,
pf5000AxrpGroupMonitoringState, pf5000AxrpGroupRingport1, pf5000AxrpGroupRingport2,
pf5200SystemMsgType, pf5200SystemMsgTimeStamp,pf5200SystemMsgLevel,
pf5200SystemMsgEventPoint, pf5200SystemMsgEventInterfaceID,
pf5200SystemMsgEventCode, pf5200SystemMsgAdditionalCode, pf5200SystemMsgText,
pf5200ChassisIndex, pf5200TemperatureStatusIndex, pf5200TemperatureStatusDescr,
pf5200TemperatureStatusValue, pf5200TemperatureState,
pf5000GsrpGroupId, pf5000GsrpVlanGroupId, pf5000GsrpState,
pf5000LoginName, pf5000LoginTime, pf5000LoginLocation, pf5000LoginLine,
pf5000LoginFailureTime, pf5000LogoutTime, pf5000LogoutStatus,
pf5000L2ldPortIndex, pf5000L2ldPortIfIndex, pf5000L2ldPortSourcePortIfindex,
pf5000L2ldPortDestinationPortIfindex, pf5000L2ldPortSourceVlan
    FROM PF5200
;

-- Traps for use by NEC PF5200

-- Traps are defined using the conventions in RFC 1215.

--pf5000AxrpStateTransitionTrap TRAP-TYPE
pf5200AxrpStateTransitionTrap TRAP-TYPE
    ENTERPRISE  pf5200TrapId
    VARIABLES {
        pf5000AxrpGroupRingId,
        pf5000AxrpGroupMode,
        pf5000AxrpGroupRingAttribute,
        pf5000AxrpGroupMonitoringState
    }
    DESCRIPTION
        "When the state of the ring of ALAXALA Ring Protocol (trouble watch and restoration watch) changes between each state. "
    ::= 36

--pf5000AxrpRingport1MonitoringStartTrap TRAP-TYPE
pf5200AxrpRingport1MonitoringStartTrap TRAP-TYPE
    ENTERPRISE  pf5200TrapId
    VARIABLES {
        pf5000AxrpGroupRingId,
        pf5000AxrpGroupMode,
        pf5000AxrpGroupRingAttribute,
        pf5000AxrpGroupRingport1
    }
    DESCRIPTION
        "When you make the link monitoring function of ring port 1 of Ring Protocol effective. "
    ::= 37

--pf5000AxrpRingport1DownTrap TRAP-TYPE
pf5200AxrpRingport1DownTrap TRAP-TYPE
    ENTERPRISE  pf5200TrapId
    VARIABLES {
        pf5000AxrpGroupRingId,
        pf5000AxrpGroupMode,
        pf5000AxrpGroupRingAttribute,
        pf5000AxrpGroupRingport1
    }
    DESCRIPTION
        "When the link for the watch is cut when the link monitoring function of ring port 1 of Ring Protocol is made effective. "
    ::= 38

--pf5000AxrpRingport2MonitoringStartTrap TRAP-TYPE
pf5200AxrpRingport2MonitoringStartTrap TRAP-TYPE
    ENTERPRISE  pf5200TrapId
    VARIABLES {
        pf5000AxrpGroupRingId,
        pf5000AxrpGroupMode,
        pf5000AxrpGroupRingAttribute,
        pf5000AxrpGroupRingport2
    }
    DESCRIPTION
        "When you make the link monitoring function of ring port 2 of Ring Protocol effective. "
    ::= 39

--pf5000AxrpRingport2DownTrap TRAP-TYPE
pf5200AxrpRingport2DownTrap TRAP-TYPE
    ENTERPRISE  pf5200TrapId
    VARIABLES {
        pf5000AxrpGroupRingId,
        pf5000AxrpGroupMode,
        pf5000AxrpGroupRingAttribute,
        pf5000AxrpGroupRingport2
    }
    DESCRIPTION
        "When the link for the watch is cut when the link monitoring function of ring port 2 of Ring Protocol is made effective. "
    ::= 40

pf5200SystemMsgTrap TRAP-TYPE
    ENTERPRISE  pf5200TrapId
    VARIABLES {
        pf5200SystemMsgType,
        pf5200SystemMsgTimeStamp,
        pf5200SystemMsgLevel,
        pf5200SystemMsgEventPoint,
        pf5200SystemMsgEventInterfaceID,
        pf5200SystemMsgEventCode,
        pf5200SystemMsgAdditionalCode,
        pf5200SystemMsgText
    }
    DESCRIPTION
        "System message is displayed."
    ::= 1

pf5200StandbySystemUpTrap TRAP-TYPE
    ENTERPRISE  pf5200TrapId
    VARIABLES  { pf5200ChassisIndex }
    DESCRIPTION
        "Standby system is restarted."
    ::= 2

pf5200StandbySystemDownTrap TRAP-TYPE
    ENTERPRISE  pf5200TrapId
    VARIABLES  { pf5200ChassisIndex }
    DESCRIPTION
        "Standby system is failed."
    ::= 3

pf5200TemperatureTrap TRAP-TYPE
    ENTERPRISE  pf5200TrapId
    VARIABLES {
        pf5200ChassisIndex,
        pf5200TemperatureStatusIndex,
        pf5200TemperatureStatusDescr, 
        pf5200TemperatureStatusValue, 
        pf5200TemperatureState
    }
    DESCRIPTION
        "A pf5200TemperatureTrap is sent if the 
        temperature measured at a given testpoint is outside 
        the normal range for the testpoint (i.e. is at the warning, 
        critical, or shutdown stage)."
    ::= 4

--pf5000GsrpStateTransitionTrap TRAP-TYPE
pf5200GsrpStateTransitionTrap TRAP-TYPE
    ENTERPRISE  pf5200TrapId
    VARIABLES {
        pf5000GsrpGroupId,
        pf5000GsrpVlanGroupId,
        pf5000GsrpState
    }
    DESCRIPTION
        "Changes of the VLAN group state of GSRP"
    ::= 6

pf5200AirFanStopTrap TRAP-TYPE
    ENTERPRISE  pf5200TrapId
    DESCRIPTION
        "This trap indicates a fan failure." 
    ::= 8 

pf5200PowerSupplyFailureTrap TRAP-TYPE
    ENTERPRISE  pf5200TrapId
    DESCRIPTION
        "This trap indicates one ( or more ) of power supplies failure." 
    ::= 9 

pf5200LoginSuccessTrap TRAP-TYPE
    ENTERPRISE  pf5200TrapId
    VARIABLES {
        pf5000LoginName,
        pf5000LoginTime,
        pf5000LoginLocation,
        pf5000LoginLine
    }
    DESCRIPTION
        "This trap indicates success of user log in." 
    ::= 10 

pf5200LoginFailureTrap TRAP-TYPE
    ENTERPRISE  pf5200TrapId
    VARIABLES {
        pf5000LoginName,
        pf5000LoginFailureTime, 
        pf5000LoginLocation,
        pf5000LoginLine
    }
    DESCRIPTION
        "This trap indicates failure of user log in." 
    ::= 11

pf5200LogoutTrap TRAP-TYPE
    ENTERPRISE  pf5200TrapId
    VARIABLES {
        pf5000LoginName,
        pf5000LoginTime,
        pf5000LogoutTime, 
        pf5000LoginLocation,
        pf5000LoginLine,
        pf5000LogoutStatus
    }
    DESCRIPTION
        "This trap indicates success of following log out.
        'logout' command, 'exit' command, 'quit' command." 
    ::= 12

pf5200MemoryUsageTrap  TRAP-TYPE
    ENTERPRISE  pf5200TrapId
    DESCRIPTION
        "This indicates available memory is fewer than lower limit." 
    ::= 13

pf5200FrameErrorReceiveTrap  TRAP-TYPE
    ENTERPRISE  pf5200TrapId
    VARIABLES  { ifIndex }
    DESCRIPTION
        "This indicates frame receive error." 
    ::= 18

pf5200FrameErrorSendTrap  TRAP-TYPE
    ENTERPRISE  pf5200TrapId
    VARIABLES  { ifIndex }
    DESCRIPTION
        "This indicates frame send error." 
    ::= 19

--pf5000BroadcastStormDetectTrap TRAP-TYPE
pf5200BroadcastStormDetectTrap TRAP-TYPE
    ENTERPRISE  pf5200TrapId
    VARIABLES  { ifIndex }
    DESCRIPTION
        "This indicates decection on broad-cast storm." 
    ::= 20

--pf5000MulticastStormDetectTrap TRAP-TYPE
pf5200MulticastStormDetectTrap TRAP-TYPE
    ENTERPRISE  pf5200TrapId
    VARIABLES  { ifIndex }
    DESCRIPTION
        "This indicates decection on multi-cast storm." 
    ::= 21

--pf5000UnicastStormDetectTrap TRAP-TYPE
pf5200UnicastStormDetectTrap TRAP-TYPE
    ENTERPRISE  pf5200TrapId
    VARIABLES  { ifIndex }
    DESCRIPTION
        "This indicates decection on uni-cast storm." 
    ::= 22

--pf5000BroadcastStormPortInactivateTrap TRAP-TYPE
pf5200BroadcastStormPortInactivateTrap TRAP-TYPE
    ENTERPRISE  pf5200TrapId
    VARIABLES  { ifIndex }
    DESCRIPTION
        "This indicates the port inactivated for decection on broad-cast storm." 
    ::= 23

--pf5000MulticastStormPortInactivateTrap TRAP-TYPE
pf5200MulticastStormPortInactivateTrap TRAP-TYPE
    ENTERPRISE  pf5200TrapId
    VARIABLES   { ifIndex }
    DESCRIPTION
        "This indicates the port inactivated for decection on multi-cast storm." 
    ::= 24

--pf5000UnicastStormPortInactivateTrap TRAP-TYPE
pf5200UnicastStormPortInactivateTrap TRAP-TYPE
    ENTERPRISE  pf5200TrapId
    VARIABLES  { ifIndex }
    DESCRIPTION
        "This indicates the port inactivated for decection on uni-cast storm." 
    ::= 25

--pf5000BroadcastStormRecoverTrap TRAP-TYPE
pf5200BroadcastStormRecoverTrap TRAP-TYPE
    ENTERPRISE  pf5200TrapId
    VARIABLES  { ifIndex }
    DESCRIPTION
        "This indicates the end of broad-cast storm." 
    ::= 26

--pf5000MulticastStormRecoverTrap TRAP-TYPE
pf5200MulticastStormRecoverTrap TRAP-TYPE
    ENTERPRISE  pf5200TrapId
    VARIABLES  { ifIndex }
    DESCRIPTION
        "This indicates the end of multi-cast storm." 
    ::= 27
    
--pf5000UnicastStormRecoverTrap TRAP-TYPE
pf5200UnicastStormRecoverTrap TRAP-TYPE
    ENTERPRISE  pf5200TrapId
    VARIABLES  { ifIndex }
    DESCRIPTION
        "This indicates the end of multi-cast storm." 
    ::= 28

--pf5000EfmoamUdldPortInactivateTrap TRAP-TYPE
pf5200EfmoamUdldPortInactivateTrap TRAP-TYPE
    ENTERPRISE  pf5200TrapId
    VARIABLES  { ifIndex }
    DESCRIPTION
        "Efmoam udld port inactivate trap."
    ::= 29

--pf5000EfmoamLoopDetectPortInactivateTrap TRAP-TYPE
pf5200EfmoamLoopDetectPortInactivateTrap TRAP-TYPE
    ENTERPRISE  pf5200TrapId
    VARIABLES  { ifIndex }
    DESCRIPTION
        "Efmoam loop detect port inactivate trap."
    ::= 30

--pf5000L2ldLinkDown TRAP-TYPE
pf5200L2ldLinkDown TRAP-TYPE
    ENTERPRISE  pf5200TrapId
    VARIABLES  {
        pf5000L2ldPortIfIndex,
        pf5000L2ldPortSourcePortIfindex,
        pf5000L2ldPortDestinationPortIfindex,
        pf5000L2ldPortSourceVlan
    }
    DESCRIPTION
        "When the operation of the interface changes from ACTIVE(state that can be communicated)
        into DISABLE (state that cannot be communicated) by the L2 loop detection."
    ::= 51

--pf5000L2ldLinkUp TRAP-TYPE
pf5200L2ldLinkUp TRAP-TYPE
    ENTERPRISE  pf5200TrapId
    VARIABLES  { pf5000L2ldPortIfIndex }
    DESCRIPTION
           "When the operation of the interface changes from DISABLE (state that cannot be communicated)
           into ACTIVE (state that can be communicated) by the automatic restoration function of the L2 loop detection."
    ::= 52

--pf5000L2ldLoopDetection TRAP-TYPE
pf5200L2ldLoopDetection TRAP-TYPE
    ENTERPRISE  pf5200TrapId
    VARIABLES {
        pf5000L2ldPortIndex,
        pf5000L2ldPortIfIndex,
        pf5000L2ldPortSourcePortIfindex,
        pf5000L2ldPortSourceVlan
    }
    DESCRIPTION
           "When you detect the L2 loop. It notifies every 60 seconds when the state of the L2 loop continues."
    ::= 53
END
